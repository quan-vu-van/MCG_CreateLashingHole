Attribute VB_Name = "ModInputHelper_V3"

Option Explicit

' ==============================================================================
' 1. HAM CHON THU CONG P1, P2 (PURE MANUAL)
' ==============================================================================
Public Function GetRectangularPoints(ByRef P1_Out As Variant, ByRef P2_Out As Variant) As Boolean
    GetRectangularPoints = False

    On Error Resume Next
    ThisDrawing.SendCommand "(princ) " & vbCr ' Fix focus CAD
    
    ' 1. Lay P1
    P1_Out = ThisDrawing.Utility.GetPoint(, vbCrLf & "1. Chon diem P1 (goc thu nhat): ")
    If Err.Number <> 0 Or IsEmpty(P1_Out) Then
        Err.Clear: Exit Function
    End If
    
    ' 2. Lay P2 (Rubber-band tu P1)
    P2_Out = ThisDrawing.Utility.GetCorner(P1_Out, vbCrLf & "2. Chon diem P2 (goc doi dien): ")
    If Err.Number <> 0 Or IsEmpty(P2_Out) Then
        Err.Clear: Exit Function
    End If
    
    On Error GoTo 0
    GetRectangularPoints = True
End Function



' 2. HAM TIM KHUNG BAO THONG MINH (SMART BOUNDING BOX) ===
' [UPDATED] Them tham so sLocationMode de xac dinh P1
Public Function GetSmartRectangularPointsFromPolyline( _
    ByVal pline As AcadLWPolyline, _
    ByRef P1_Out As Variant, ByRef P2_Out As Variant, _
    ByVal sLocationMode As String _
) As Boolean
    
    GetSmartRectangularPointsFromPolyline = False
    
    Dim coords As Variant
    coords = pline.Coordinates
    
    Dim i As Long, numVerts As Long
    numVerts = (UBound(coords) + 1) / 2
    
    Const LENGTH_THRESHOLD As Double = 1500#
    
    Dim minX As Double, maxX As Double, minY As Double, maxY As Double
    Dim foundX As Boolean, foundY As Boolean
    foundX = False: foundY = False
    
    ' Khoi tao gia tri vo cuc
    minX = 1E+30: maxX = -1E+30
    minY = 1E+30: maxY = -1E+30
    
    Dim x1 As Double, y1 As Double, x2 As Double, y2 As Double
    Dim bulge As Double
    Dim segLen As Double, deltaX As Double, deltaY As Double
    
    ' --- Logic 1: Quet Min/Max nhu cu ---
    For i = 0 To numVerts - 1
        x1 = coords(2 * i)
        y1 = coords(2 * i + 1)
        
        Dim nextIdx As Long
        nextIdx = (i + 1) Mod numVerts
        x2 = coords(2 * nextIdx)
        y2 = coords(2 * nextIdx + 1)
        
        bulge = pline.GetBulge(i)
        If Abs(bulge) < 0.001 Then
            deltaX = Abs(x2 - x1)
            deltaY = Abs(y2 - y1)
            segLen = Sqr(deltaX ^ 2 + deltaY ^ 2)
            
            If segLen > LENGTH_THRESHOLD Then
                If deltaX < 1# Then  ' Doan doc
                    If x1 < minX Then minX = x1
                    If x1 > maxX Then maxX = x1
                    foundX = True
                End If
                If deltaY < 1# Then  ' Doan ngang
                    If y1 < minY Then minY = y1
                    If y1 > maxY Then maxY = y1
                    foundY = True
                End If
            End If
        End If
    Next i
    
    ' Fallback neu khong tim thay
    If Not foundX Or Not foundY Then
        Dim minPt As Variant, maxPt As Variant
        pline.GetBoundingBox minPt, maxPt
        If Not foundX Then minX = minPt(0): maxX = maxPt(0)
        If Not foundY Then minY = minPt(1): maxY = maxPt(1)
    End If
    
    ' --- Logic 2: [NEW] Gan P1, P2 dua theo LocationOption ---
    Dim p1(0 To 2) As Double, p2(0 To 2) As Double
    
    Select Case sLocationMode
        Case "StarBoard"
            ' P1 = (Xmin, Ymax) -> P2 phai la (Xmax, Ymin)
            p1(0) = minX: p1(1) = maxY: p1(2) = 0
            p2(0) = maxX: p2(1) = minY: p2(2) = 0
            
        Case "PortSide", "Center"
            ' P1 = (Xmin, Ymin) -> P2 la (Xmax, Ymax) (Mac dinh cu)
            p1(0) = minX: p1(1) = minY: p1(2) = 0
            p2(0) = maxX: p2(1) = maxY: p2(2) = 0
            
        Case Else
            ' Fallback mac dinh
            p1(0) = minX: p1(1) = minY: p1(2) = 0
            p2(0) = maxX: p2(1) = maxY: p2(2) = 0
    End Select
    
    P1_Out = p1
    P2_Out = p2
    GetSmartRectangularPointsFromPolyline = True

End Function
' ==========================================================================================
' === FUNCTION TO SELECT BOUNDARY (UPDATED: ALLOW OPEN POLYLINE) ===
' Requirement: LWPolyline, Layer: Mechanical-AM_0, Area > 20m2
Public Function SelectBoundaryPolyline_Helper() As AcadLWPolyline
    Dim ss As AcadSelectionSet
    Dim filterType(0 To 1) As Integer
    Dim filterData(0 To 1) As Variant
    Dim element As AcadEntity
    Dim polyObj As AcadLWPolyline
    Dim ssName As String

    On Error GoTo BoundaryErr

    ' 1. Create new SelectionSet (delete if exists)
    ssName = "SS_Boundary_Filter"
    On Error Resume Next
    ThisDrawing.SelectionSets.Item(ssName).Delete
    On Error GoTo BoundaryErr
    Set ss = ThisDrawing.SelectionSets.Add(ssName)

    ' 2. Set up Filter
    ' DXF Code 0: Object Type
    ' DXF Code 8: Layer Name
    filterType(0) = 0: filterData(0) = "LWPOLYLINE"
    filterType(1) = 8: filterData(1) = "0,Mechanical-AM_0" ' <--- Required Layer

    ' 3. Execute selection
    ThisDrawing.Utility.prompt vbCrLf & ">>> Select Boundary (Polyline, Layer Mechanical-AM_0 ): "

    ' Fix CAD Focus hang issue
    ThisDrawing.SendCommand "(princ) " & vbCr

    ' Select on screen with filter
    ss.SelectOnScreen filterType, filterData

    ' 4. Check result
    If ss.Count = 0 Then
        MsgBox "No Polyline found on layer '0 or Mechanical-AM_0' in selection.", vbExclamation
        Set SelectBoundaryPolyline_Helper = Nothing
        ss.Delete
        Exit Function
    End If

    ' 5. Iterate through selected objects
    ' [UPDATED] Removed Check Closed property logic
    Dim foundValid As Boolean: foundValid = False

    For Each element In ss
        If TypeOf element Is AcadLWPolyline Then
            Set polyObj = element
            
            ' [EDITED LINE] Removed "polyObj.Closed = True And"
            ' Still keep Area check to avoid selecting small debris
            If Round(polyObj.Area / 1000000#, 0) > 20 Then
                Set SelectBoundaryPolyline_Helper = polyObj
                foundValid = True
                Exit For ' Exit immediately if found
            End If
        End If
    Next element

    ' 6. Handle if valid object not found
    If Not foundValid Then
        ' Updated error message to reflect the change
        MsgBox "Selected object is too small (< 20m2) or not on correct Layer!", vbExclamation
        Set SelectBoundaryPolyline_Helper = Nothing
    Else
        ThisDrawing.Utility.prompt vbCrLf & "-> Boundary selected successfully."
    End If

    ' Cleanup
    ss.Delete
    Exit Function

BoundaryErr:
    MsgBox "Error in SelectBoundaryPolyline_Helper: " & Err.Description, vbCritical
    If Not ss Is Nothing Then ss.Delete
    Set SelectBoundaryPolyline_Helper = Nothing
End Function

Public Function GetNameInPanel(ByVal crvPoly As Object) As Variant
    
    Dim ssetObj As AcadSelectionSet
    Dim filterType(0) As Integer
    Dim filterData(0) As Variant
                
    Dim i As Integer
    Dim iText As Integer, ntexts As Integer
    Dim myText As AcadEntity ' Changed to Generic Entity to handle both Text and MText
    Dim panelString As String
    
    Dim dblCoords As Variant
    dblCoords = crvPoly.Coordinates
    
    Dim bbox() As Double
    bbox = GetBoundingBoxFrmPolyline(dblCoords)
                    
    ' Clean up selection set
    For Each ssetObj In ThisDrawing.SelectionSets
       If ssetObj.Name = "SelectText" Then
           ThisDrawing.SelectionSets("SelectText").Delete
           Exit For
       End If
    Next
    
    Dim SpecialLetter() As String
    SpecialLetter = Split("{,},C1,\pxqc,;,\L,R,%%U,\A", ",")
            
    Set ssetObj = MeSelectionSet("SelectText")
    filterType(0) = 0: filterData(0) = "TEXT,MTEXT"
    
    ' Select text inside the polygon
    ssetObj.SelectByPolygon acSelectionSetWindowPolygon, bbox, filterType, filterData
    
    ntexts = ssetObj.Count
    If ssetObj.Count > 0 Then
        For iText = 0 To ntexts - 1
            Set myText = ssetObj.Item(iText)
            
            ' Handle TextString property for both Text and MText
            If TypeOf myText Is AcadText Then
                panelString = myText.TextString
            ElseIf TypeOf myText Is AcadMText Then
                panelString = myText.TextString
            End If

            ' Remove special formatting characters
            For i = 0 To UBound(SpecialLetter)
                panelString = Replace(panelString, SpecialLetter(i), "")
            Next i
                
        Next iText
    End If
    
    GetNameInPanel = panelString
    
End Function

Public Function MeSelectionSet(SetMe As String) As AcadSelectionSet
    Dim selSet As AcadSelectionSet  ' Selection set entity
    Dim SelCol As AcadSelectionSets ' Selection set collection
    
    With ThisDrawing
        Set SelCol = .SelectionSets
        For Each selSet In SelCol
            If selSet.Name = SetMe Then
                .SelectionSets.Item(SetMe).Delete
                Exit For
            End If
        Next
        Set MeSelectionSet = .SelectionSets.Add(SetMe)
    End With
End Function

Public Function GetAcad() As AcadApplication
    ' Get AutoCAD Application Object
    Dim acadApp As AcadApplication
    
    ' Autocad Session handling
    On Error Resume Next
    Set acadApp = GetObject(, "Autocad.Application")
    If Err.Number <> 0 Then
        Err.Clear
        Set acadApp = CreateObject("Autocad.Application")
    End If
    On Error GoTo 0
    
    acadApp.Visible = True
    Set GetAcad = acadApp
End Function

Public Function pathLink() As String
    pathLink = "C:\CustomTools\Outputs\"
End Function

Public Function GetBoundingBoxFrmPolyline(coords As Variant) As Double()
    ' Function returns 3D array (x, y, 0) for use with SelectByPolygon
    ' Automatically closes the polyline if it is open
    
    Dim i As Long, j As Long
    Dim ub As Long
    Dim xStart As Double, yStart As Double
    Dim xEnd As Double, yEnd As Double
    Dim isClosed As Boolean
    Dim result() As Double
    
    ub = UBound(coords)
    
    ' Get start point
    xStart = coords(0)
    yStart = coords(1)
    
    ' Get end point
    xEnd = coords(ub - 1)
    yEnd = coords(ub)
    
    ' Check if closed (Compare with small epsilon)
    If Abs(xStart - xEnd) < 0.0001 And Abs(yStart - yEnd) < 0.0001 Then
        isClosed = True
    Else
        isClosed = False
    End If
    
    ' Calculate array size
    ' Each 2D point becomes 3D (add Z=0) -> factor 1.5
    ' If not closed, add 1 more point (3 elements) to close it
    If isClosed Then
        ReDim result(0 To ((ub + 1) / 2 * 3) - 1)
    Else
        ReDim result(0 To ((ub + 1) / 2 * 3) + 2)
    End If
    
    ' Loop convert 2D -> 3D
    j = 0
    For i = 0 To ub Step 2
        result(j) = coords(i)       ' X
        result(j + 1) = coords(i + 1) ' Y
        result(j + 2) = 0           ' Z
        j = j + 3
    Next i
    
    ' If not closed, append start point to end
    If Not isClosed Then
        result(j) = xStart
        result(j + 1) = yStart
        result(j + 2) = 0
    End If
    
    GetBoundingBoxFrmPolyline = result
End Function

Public Function DistanceBetweenPoints(pt1 As Variant, pt2 As Variant, Optional includeZ As Boolean = False) As Double
    ' Calculate Euclidean distance between two points (2D or 3D)
    If UBound(pt1) < 0 Or UBound(pt2) < 0 Then Exit Function
    
    Dim dx As Double: dx = pt2(0) - pt1(0)
    Dim dy As Double: dy = pt2(1) - pt1(1)
    Dim dz As Double: dz = 0
    
    If includeZ And UBound(pt1) >= 2 And UBound(pt2) >= 2 Then
        dz = pt2(2) - pt1(2)
    End If
    
    DistanceBetweenPoints = Sqr(dx * dx + dy * dy + dz * dz)
End Function


' Hàm này trích xu?t danh sách các Layer duy nh?t t? m?t SelectionSet thành chu?i (VD: "Layer1,Layer2")
Public Function GetLayersFromSelectionSet(ss As AcadSelectionSet) As String
    Dim obj As AcadEntity
    Dim dict As Object
    Set dict = CreateObject("Scripting.Dictionary")
    dict.CompareMode = vbTextCompare
    
    Dim layList As String
    
    On Error Resume Next
    For Each obj In ss
        If Not dict.Exists(obj.Layer) Then
            dict.Add obj.Layer, 1
            layList = layList & obj.Layer & ","
        End If
    Next obj
    On Error GoTo 0
    
    If Len(layList) > 0 Then
        ' Xóa d?u ph?y cu?i cùng
        GetLayersFromSelectionSet = Left(layList, Len(layList) - 1)
    End If
End Function

Attribute VB_Name = "frmHelpDialog"
Attribute VB_Base = "0{4FA9C5CD-6CE4-4E4E-BA30-DF6D988F93CC}{14A21D25-7F9E-4D56-8590-269B8D1C189F}"
Attribute VB_GlobalNameSpace = False
Attribute VB_Creatable = False
Attribute VB_PredeclaredId = True
Attribute VB_Exposed = False
Attribute VB_TemplateDerived = False
Attribute VB_Customizable = False
Option Explicit

Private Declare PtrSafe Function FindWindow Lib "user32" Alias "FindWindowA" (ByVal lpClassName As String, ByVal lpWindowName As String) As LongPtr
' Trong 64-bit, ph?i dùng hàm GetWindowLongPtr và SetWindowLongPtr
Private Declare PtrSafe Function GetWindowLongPtr Lib "user32" Alias "GetWindowLongPtrA" (ByVal hWnd As LongPtr, ByVal nIndex As Long) As LongPtr
Private Declare PtrSafe Function SetWindowLongPtr Lib "user32" Alias "SetWindowLongPtrA" (ByVal hWnd As LongPtr, ByVal nIndex As Long, ByVal dwNewLong As LongPtr) As LongPtr


Private Const GWL_STYLE As Long = -16
Private Const WS_THICKFRAME As Long = &H40000      ' Cho phép kéo giãn vi?n
Private Const WS_MAXIMIZEBOX As Long = &H10000     ' Hi?n nút Maximize
Private Const WS_MINIMIZEBOX As Long = &H20000     ' Hi?n nút Minimize

Private m_hWnd As LongPtr



' ==============================================================================
' INITIALIZATION & ACTIVATION
' ==============================================================================
Private Sub UserForm_Activate()
    ' 1. Make the Form Resizable
    m_hWnd = FindWindow("ThunderDFrame", Me.Caption)
    If m_hWnd <> 0 Then
        Dim currentStyle As LongPtr
        Dim newStyle As LongPtr
        currentStyle = GetWindowLongPtr(m_hWnd, GWL_STYLE)
        newStyle = currentStyle Or WS_THICKFRAME Or WS_MAXIMIZEBOX Or WS_MINIMIZEBOX
        SetWindowLongPtr m_hWnd, GWL_STYLE, newStyle
    End If
    
    ' 2. Load Content
    LoadHelpContent
End Sub

' ==============================================================================
' RESIZE EVENT (Keeps WebBrowser filling the form)
' ==============================================================================
Private Sub UserForm_Resize()
    On Error Resume Next
    Const MARGIN As Double = 6
    
    If Me.InsideWidth < 50 Or Me.InsideHeight < 50 Then Exit Sub
    
    ' Ensure your WebBrowser control is named "webHelp"
    With Me.webHelp
        .Left = MARGIN
        .top = MARGIN
        .Width = Me.InsideWidth - (MARGIN * 2)
        .Height = Me.InsideHeight - (MARGIN * 2)
    End With
End Sub

' ==============================================================================
' CONTENT LOADER (UPDATED TEXT)
' ==============================================================================
Private Sub LoadHelpContent()
    Dim sHTML As String
    
    ' CSS Styling for clean look
    sHTML = "<html><body style='font-family: Segoe UI, Arial, sans-serif; font-size: 10pt; background-color: #f9f9f9; padding: 10px; line-height: 1.4;'>"
    
    ' --- HEADER ---
    sHTML = sHTML & "<h3 style='color: #003366; border-bottom: 2px solid #003366; padding-bottom: 5px; margin-top: 0;'>LASHING HOLE GENERATOR - USER GUIDE</h3>"
    
    ' --- STEP 1 ---
    sHTML = sHTML & "<div style='margin-bottom: 15px;'>"
    sHTML = sHTML & "<strong style='color: #cc0000; font-size: 11pt;'>[STEP 1] PREPARATION</strong>"
    sHTML = sHTML & "<ul style='margin-top: 5px;'>"
    sHTML = sHTML & "<li>Draw the Top Plate boundary as a <b>Closed Polyline</b> (Layer '0' or 'Mechanical-AM_0').</li>"
    sHTML = sHTML & "<li>Select structures to <b>avoid collisions</b>, including the Top Plate boundary itself.</li>"
    sHTML = sHTML & "</ul></div>"
    
    ' --- STEP 2 ---
    sHTML = sHTML & "<div style='margin-bottom: 15px;'>"
    sHTML = sHTML & "<strong style='color: #cc0000; font-size: 11pt;'>[STEP 2] INPUT PARAMETERS</strong>"
    sHTML = sHTML & "<ul style='margin-top: 5px;'>"
    sHTML = sHTML & "<li><b>Spacing X/Y:</b> Distance between hole centers.</li>"
    sHTML = sHTML & "<li><b>Offset X/Y:</b> Distance from hole to boundary edge.</li>"
    sHTML = sHTML & "<li><b>Hole Diameter & Clearance:</b> Define hole size and safety zone.</li>"
    sHTML = sHTML & "</ul></div>"
    
    ' --- STEP 3 (UPDATED LOGIC) ---
    sHTML = sHTML & "<div style='margin-bottom: 15px;'>"
    sHTML = sHTML & "<strong style='color: #cc0000; font-size: 11pt;'>[STEP 3] EXECUTION MODES</strong>"
    
    ' Automatic Mode Logic
    sHTML = sHTML & "<p style='margin-bottom:5px;'><b>1. Automatic Mode (Checked):</b></p>"
    sHTML = sHTML & "<ul style='margin-top: 0;'>"
    sHTML = sHTML & "<li>Tool automatically selects Anchor Points (P1, P2) and direction based on Panel Location:</li>"
    sHTML = sHTML & "<li><b>PS (PortSide) & C (Center):</b> P1 = Lower-Left, P2 = Upper-Right.</li>"
    sHTML = sHTML & "<li><b>SB (StarBoard):</b> P1 = Upper-Left, P2 = Lower-Right.</li>"
    sHTML = sHTML & "</ul>"
    
    ' Manual Mode Logic
    sHTML = sHTML & "<p style='margin-bottom:5px;'><b>2. Manual Mode (Unchecked):</b></p>"
    sHTML = sHTML & "<ul style='margin-top: 0;'>"
    sHTML = sHTML & "<li>You must manually select Anchor Points <b>P1 and P2</b>.</li>"
    sHTML = sHTML & "<li>Define the hole generation direction.</li>"
    sHTML = sHTML & "<li>Select the <b>Initial Insertion Point</b> (Choose a position that intersects the most structures for best alignment).</li>"
    sHTML = sHTML & "</ul></div>"
    
    ' --- STEP 4 (UPDATED BUTTON NAME) ---
    sHTML = sHTML & "<div style='margin-bottom: 15px;'>"
    sHTML = sHTML & "<strong style='color: #cc0000; font-size: 11pt;'>[STEP 4] RESULTS & CHECKS</strong>"
    sHTML = sHTML & "<ul style='margin-top: 5px;'>"
    sHTML = sHTML & "<li>A Block containing holes and dimensions will be created.</li>"
    sHTML = sHTML & "<li><span style='color:red; font-weight:bold'>RED</span> circles indicate collisions.</li>"
    sHTML = sHTML & "<li>Use the <b>'Check Interference'</b> button to verify interference between existing lashing holes and structures.</li>"
    sHTML = sHTML & "</ul></div>"
    
    ' --- FOOTER ---
    sHTML = sHTML & "<br>" ' Add a little spacing
    sHTML = sHTML & "<hr style='border: 0; border-top: 1px solid #ccc;'>"
    
    ' Styled contact info centered at the bottom
    sHTML = sHTML & "<div style='font-size: 9pt; color: #555; text-align: center; padding-top: 5px;'>"
    sHTML = sHTML & "If you have any questions, please contact developer team: <b>quan.vuvan@macgregor.com</b>"
    sHTML = sHTML & "</div>"
    
    sHTML = sHTML & "</body></html>"
    
    ' Render content
    On Error Resume Next
    Me.webHelp.Navigate "about:blank"
    DoEvents
    Me.webHelp.Document.Write sHTML
    On Error GoTo 0
End Sub

Private Sub UserForm_Click()
    Me.Hide
End Sub

Attribute VB_Name = "frmLashingInput"
Attribute VB_Base = "0{2396F0C8-7223-4232-8FB0-C7854ED49501}{CD437CB5-7AE9-4046-8FEF-41323EA5ED16}"
Attribute VB_GlobalNameSpace = False
Attribute VB_Creatable = False
Attribute VB_PredeclaredId = True
Attribute VB_Exposed = False
Attribute VB_TemplateDerived = False
Attribute VB_Customizable = False

Option Explicit


' ==============================================================================
' REGISTRY CONSTANTS (For saving/loading settings)
' ==============================================================================
Private Const APP_NAME As String = "AutoCAD_LashingTools"
Private Const SECTION_NAME As String = "HoleGenSettings"

' ==============================================================================
' PUBLIC VARIABLES (ACCESSED BY MAIN MODULE)
' ==============================================================================
Public IsCancelled As Boolean
Public ActionType As String         ' "Create" or "Audit"

' -- Dimensions --
Public holeDiameter As Double
Public clearanceRadius As Double
Public offsetX As Double
Public offsetY As Double
Public spacingX As Double
Public spacingY As Double

' -- Logic Parameters --
Public IsAutomaticMode As Boolean   ' Checkbox: Auto-detect boundary
Public IsCheckAdjacent As Boolean   ' Checkbox: Check adjacent panels
Public PanelName As String          ' Textbox: Panel Name
Public LocationMode As String       ' Option: "PortSide", "StarBoard", "Center"



' ==============================================================================
' INITIALIZATION
' ==============================================================================
Private Sub UserForm_Initialize()
    
    ' 1. Load settings from Registry (GetSetting)
    ' Syntax: GetSetting(AppName, Section, Key, DefaultValue)
    
    ' -- TextBoxes --
    Me.txtHoleDiameter.Text = GetSetting(APP_NAME, SECTION_NAME, "HoleDiameter", "55")
    Me.txtClearanceRadius.Text = GetSetting(APP_NAME, SECTION_NAME, "ClearanceRadius", "75")
    Me.txtOffsetX.Text = GetSetting(APP_NAME, SECTION_NAME, "OffsetX", "150")
    Me.txtOffsetY.Text = GetSetting(APP_NAME, SECTION_NAME, "OffsetY", "150")
    Me.txtSpacingX.Text = GetSetting(APP_NAME, SECTION_NAME, "SpacingX", "500")
    Me.txtSpacingY.Text = GetSetting(APP_NAME, SECTION_NAME, "SpacingY", "500")
    Me.txtPanelName.Text = GetSetting(APP_NAME, SECTION_NAME, "PanelName", "PNL_01")

    ' -- Checkboxes (Stored as Strings "True"/"False", convert back to Boolean) --
    Me.chkAutomatic.Value = CBool(GetSetting(APP_NAME, SECTION_NAME, "IsAutomatic", "True"))
    Me.chkCheckAdjacent.Value = CBool(GetSetting(APP_NAME, SECTION_NAME, "IsCheckAdjacent", "False"))
    
    ' -- Option Buttons (Stored as String identifier) --
    Dim savedLocMode As String
    savedLocMode = GetSetting(APP_NAME, SECTION_NAME, "LocationMode", "PortSide")
    
    Select Case savedLocMode
        Case "PortSide": Me.optPortSide.Value = True
        Case "StarBoard": Me.optStarBoard.Value = True
        Case "Center": Me.optCenter.Value = True
        Case Else: Me.optPortSide.Value = True
    End Select
    
    ' =========================================================================
    ' 1. TEXTBOXES (Input Parameters)
    ' =========================================================================
    
    ' Spacing
    txtSpacingX.ControlTipText = "Horizontal spacing between hole centers (mm)."
    txtSpacingY.ControlTipText = "Vertical spacing between hole centers (mm)."
    
    ' Offset
    txtOffsetX.ControlTipText = "Horizontal offset distance from the start point (mm)."
    txtOffsetY.ControlTipText = "Vertical offset distance from the start point (mm)."
    
    ' Geometry
    txtHoleDiameter.ControlTipText = "Diameter of the lashing hole to be cut (mm)."
    txtClearanceRadius.ControlTipText = "Safety radius buffer zone. Structures inside this zone will trigger a collision."
    
    txtPanelName.ControlTipText = "Input panel's name here to generate the lashing hole's block later on."
    
    ' =========================================================================
    ' 2. OPTION BUTTONS (Generation Method)
    ' =========================================================================
    optPortSide.ControlTipText = "Equipment is at the Postside of the vessel, the point P1 is at the LOWER left corner, P2 is at the UPPER right corner"
    optStarBoard.ControlTipText = "Equipment is at the Startboard of the vessel, the point P1 is at the UPPER left corner, P2 is at the LOWER right corner"
    optCenter.ControlTipText = "Equipment is at the Center of the vessel, the point P1 is at the LOWER left corner, P2 is at the UPPER right corner"
    
    ' =========================================================================
    ' 3. CHECKBOXES (Settings & Flags)
    ' =========================================================================
    
    ' Collision Settings
    chkAutomatic.ControlTipText = "Automatically select the point P1, P2 and the direction to generate holes. If not users need to be do manually"
    chkCheckAdjacent.ControlTipText = "If checked, the structures of the adjacent panels will be refered to generate the lashing holes of the current panel"
    
    ' =========================================================================
    ' 4. COMMAND BUTTONS
    ' =========================================================================
    cmdAudit.ControlTipText = "Check the collision between lashing holes and the structures (lashing holes and panel's structure need to be out of the blocks)"
    
    ' 2. Initialize State
    Me.IsCancelled = True
    Me.ActionType = ""
    
End Sub

' ==============================================================================
' SU KIEN NUT BAM
' ==============================================================================

' Nut Cancel: Huy lenh
Private Sub cmdCancel_Click()
    Me.IsCancelled = True
    Me.ActionType = ""
    Me.Hide
End Sub

Private Sub cmdOK_Click()
    ' 1. Validate Input
    If Not ValidateInput() Then Exit Sub
    
    ' 2. Save settings to Registry for next time
    SaveSettingsToRegistry
    
    ' 3. Transfer values to Public Variables for the Main Module
    SaveValuesToPublicVars
    
    ' 4. Update Status and Hide Form
    Me.IsCancelled = False
    Me.ActionType = "Create"
    Me.Hide
End Sub

' Nut Audit: Chay lenh kiem tra (Audit)
Private Sub cmdAudit_Click()

    Dim ACAD As AcadApplication
    Set ACAD = GetObject(, "AutoCAD.Application")
    
    Dim currentAutoStatus As Boolean
    currentAutoStatus = Me.chkAutomatic.Value
    
    Me.Hide
    
    Call CheckLashingHole_InterferenceStructure(ACAD, currentAutoStatus)
    
    'Me.show
    
End Sub

' ==============================================================================
' HELPER SUBROUTINES
' ==============================================================================

' Purpose: Save current form values to Windows Registry
Private Sub SaveSettingsToRegistry()
    On Error Resume Next
    
    ' Save TextBoxes
    SaveSetting APP_NAME, SECTION_NAME, "HoleDiameter", Me.txtHoleDiameter.Text
    SaveSetting APP_NAME, SECTION_NAME, "ClearanceRadius", Me.txtClearanceRadius.Text
    SaveSetting APP_NAME, SECTION_NAME, "OffsetX", Me.txtOffsetX.Text
    SaveSetting APP_NAME, SECTION_NAME, "OffsetY", Me.txtOffsetY.Text
    SaveSetting APP_NAME, SECTION_NAME, "SpacingX", Me.txtSpacingX.Text
    SaveSetting APP_NAME, SECTION_NAME, "SpacingY", Me.txtSpacingY.Text
    SaveSetting APP_NAME, SECTION_NAME, "PanelName", Trim(Me.txtPanelName.Text)
    
    ' Save Checkboxes
    SaveSetting APP_NAME, SECTION_NAME, "IsAutomatic", CStr(Me.chkAutomatic.Value)
    SaveSetting APP_NAME, SECTION_NAME, "IsCheckAdjacent", CStr(Me.chkCheckAdjacent.Value)
    
    ' Save Option Button
    Dim sLocMode As String
    If Me.optPortSide.Value Then sLocMode = "PortSide"
    If Me.optStarBoard.Value Then sLocMode = "StarBoard"
    If Me.optCenter.Value Then sLocMode = "Center"
    SaveSetting APP_NAME, SECTION_NAME, "LocationMode", sLocMode
    
    On Error GoTo 0
End Sub

' Purpose: Transfer values from GUI controls to Public Variables
Private Sub SaveValuesToPublicVars()
    On Error Resume Next
    
    ' numeric values
    Me.holeDiameter = CDbl(Me.txtHoleDiameter.Text)
    Me.clearanceRadius = CDbl(Me.txtClearanceRadius.Text)
    Me.offsetX = CDbl(Me.txtOffsetX.Text)
    Me.offsetY = CDbl(Me.txtOffsetY.Text)
    Me.spacingX = CDbl(Me.txtSpacingX.Text)
    Me.spacingY = CDbl(Me.txtSpacingY.Text)
    
    ' Logic parameters
    Me.IsAutomaticMode = Me.chkAutomatic.Value
    Me.IsCheckAdjacent = Me.chkCheckAdjacent.Value
    Me.PanelName = Trim(Me.txtPanelName.Text)
    
    ' Option Button Logic
    If Me.optPortSide.Value = True Then
        Me.LocationMode = "PortSide"
    ElseIf Me.optStarBoard.Value = True Then
        Me.LocationMode = "StarBoard"
    ElseIf Me.optCenter.Value = True Then
        Me.LocationMode = "Center"
    Else
        Me.LocationMode = "PortSide" ' Default fallback
    End If
    
    On Error GoTo 0
End Sub

' Purpose: Check if user input is valid
Private Function ValidateInput() As Boolean
    ValidateInput = True
    
    ' 1. Check Panel Name
    If Trim(Me.txtPanelName.Text) = "" Then
        MsgBox "Please enter Panel Name (e.g., PNL_01).", vbExclamation, "Missing Information"
        Me.txtPanelName.SetFocus
        ValidateInput = False
        Exit Function
    End If

    ' 2. Check Numeric Values
    ' Hole Diameter
    If Not IsNumeric(Me.txtHoleDiameter.Text) Or CDbl(Me.txtHoleDiameter.Text) <= 0 Then
        MsgBox "Hole Diameter must be > 0.", vbExclamation
        Me.txtHoleDiameter.SetFocus: ValidateInput = False: Exit Function
    End If
    
    ' Clearance Radius
    If Not IsNumeric(Me.txtClearanceRadius.Text) Or CDbl(Me.txtClearanceRadius.Text) <= 0 Then
        MsgBox "Clearance Radius must be > 0.", vbExclamation
        Me.txtClearanceRadius.SetFocus: ValidateInput = False: Exit Function
    End If
    
    ' Logical Check: Clearance vs Diameter
    If CDbl(Me.txtClearanceRadius.Text) < (CDbl(Me.txtHoleDiameter.Text) / 2) Then
         MsgBox "Clearance Radius must be larger than Hole Radius.", vbExclamation
         Me.txtClearanceRadius.SetFocus: ValidateInput = False: Exit Function
    End If
    
    ' Offsets
    If Not IsNumeric(Me.txtOffsetX.Text) Then
        MsgBox "Invalid Offset X.", vbExclamation
        Me.txtOffsetX.SetFocus: ValidateInput = False: Exit Function
    End If
    If Not IsNumeric(Me.txtOffsetY.Text) Then
        MsgBox "Invalid Offset Y.", vbExclamation
        Me.txtOffsetY.SetFocus: ValidateInput = False: Exit Function
    End If
    
    ' Spacing
    If Not IsNumeric(Me.txtSpacingX.Text) Or CDbl(Me.txtSpacingX.Text) <= 0 Then
        MsgBox "Spacing X must be > 0.", vbExclamation
        Me.txtSpacingX.SetFocus: ValidateInput = False: Exit Function
    End If
    If Not IsNumeric(Me.txtSpacingY.Text) Or CDbl(Me.txtSpacingY.Text) <= 0 Then
        MsgBox "Spacing Y must be > 0.", vbExclamation
        Me.txtSpacingY.SetFocus: ValidateInput = False: Exit Function
    End If
End Function

' Event: User clicks the X button on the window
Private Sub UserForm_QueryClose(Cancel As Integer, CloseMode As Integer)
    If CloseMode = vbFormControlMenu Then
        ' Treat as Cancel
        Me.IsCancelled = True
        Me.ActionType = ""
        Cancel = 1  ' Prevent actual destruction of the form object
        Me.Hide     ' Just hide it
    End If
End Sub
Private Sub cmdHelp_Click()
    Dim f As New frmHelpDialog
    f.show
End Sub

Attribute VB_Name = "mod_LashingHoleInterference"
Option Explicit


Public Sub CheckLashingHole_InterferenceStructure(ACAD As AcadApplication, ByVal isAutoMode As Boolean)

    Dim ssetObj As AcadSelectionSet
    Dim ssetObj_Inside As AcadSelectionSet
    Dim filterType As Variant
    Dim filterData As Variant
    
    Dim ThisDrawing As AcadDocument
    Set ThisDrawing = ACAD.ActiveDocument
    
    Dim LWPoly As AcadEntity
    Dim newLWPoly As AcadLWPolyline

    ' Clean up existing selection sets
    For Each ssetObj In ThisDrawing.SelectionSets
        If ssetObj.Name = "MySel" Then
           ThisDrawing.SelectionSets("MySel").Delete
           Exit For
        End If
    Next

    '*******************************************************************************
    '******************* GET BLOCK FROM SYMBOL DWG FILE ****************************
    '*******************************************************************************
    
    Dim txtLink As String
    txtLink = "C:\CustomTools\"
    
    Dim strPath As String
    Dim strBlockName As String
    Dim objBlock As acadBlock
    Dim objBlock_Mark As AcadBlockReference
    
    strBlockName = "LashingInterfereCloudMark"
    strPath = txtLink & "Symbol.dwg"
    
    ' Check if block exists, if not, copy from source file
    On Error Resume Next
    Set objBlock = ThisDrawing.Blocks.Item(strBlockName)
    If objBlock Is Nothing Then
        DbxCopyBlock strBlockName, strPath ' Copy block into ThisDrawing
        Err.Clear
    End If
    On Error GoTo 0

    '*******************************************************************************
    '******************* SELECT TOP PLATE (USER INPUT) *****************************
    '*******************************************************************************

    Set ssetObj = MeSelectionSet("MySel") ' Call function MeSelectionSet
    
    ' --- UPDATED FILTER: REMOVED LAYER RESTRICTION ---
    ' Ch? l?c theo lo?i d?i tu?ng là LWPOLYLINE, không quan tâm Layer nào
    Dim grpCode(0 To 0) As Integer
    Dim grpValue(0 To 0) As Variant
    
    grpCode(0) = 0
    grpValue(0) = "LWPOLYLINE"          ' Entity type
   
    filterType = grpCode
    filterData = grpValue

    ' Prompt user to select LWPolylines (Updated message)
    ThisDrawing.Utility.prompt vbCrLf & "Select Top Plate (the outer Polyline)!"
    
    On Error Resume Next
    ssetObj.SelectOnScreen filterType, filterData
    On Error GoTo 0
    
    ' Collections to store classified objects
    Dim beamWebPlate_Col As New Collection
    Dim lashingOuterHole_Col As New Collection
    Dim topPlate_Col As New Collection
    
    Dim inside_PolyObj As AcadEntity
    Dim toppPlateCoords As Variant
    Dim panelString As String
    
    ' Variables for Loop
    Dim irow As Integer
    Dim countpoly As Integer
    Dim areaCheck As Boolean ' Variable to track if any valid polyline was processed
    areaCheck = False
    
    If ssetObj.Count > 0 Then
        irow = 0
        countpoly = 0
        
        For Each LWPoly In ssetObj
            
            ' Reset collections for each top plate processed
            Set beamWebPlate_Col = Nothing
            Set lashingOuterHole_Col = Nothing
            Set topPlate_Col = Nothing
            Set beamWebPlate_Col = New Collection
            Set lashingOuterHole_Col = New Collection
            Set topPlate_Col = New Collection
            
            If TypeOf LWPoly Is AcadLWPolyline Then
            
                ' Check Area: Select polyline with area bigger than 20m^2 only (20,000,000 mm2)
                If Round(LWPoly.Area / 1000000#, 0) > 20 Then
                    
                    areaCheck = True ' Mark that we found at least one valid plate
                    
                    ' Process directly if already closed
                    toppPlateCoords = LWPoly.Coordinates
                    panelString = GetNameInPanel(LWPoly)
                    topPlate_Col.Add LWPoly
                            
                    '*******************************************************************************
                    '******************* SELECT OBJECTS INSIDE TOP PLATE ***************************
                    '*******************************************************************************
                    
                    Dim bbox() As Double
                    bbox = GetBoundingBoxFrmPolyline(toppPlateCoords)
                  
                    Set ssetObj_Inside = MeSelectionSet("Select_Inside")
                    
                        ' Keep filter for internal objects (Web plate, lashing hole) as per original logic?
                        ' Assuming internal objects still need to be on specific layers (AM_0, AM_3, AM_9)
                        ' If you want to remove layer restriction for internal objects too, let me know.
                        Dim grpCodeIn(0 To 1) As Integer
                        Dim grpValueIn(0 To 1) As Variant
                        
                        grpCodeIn(0) = 8
                        grpCodeIn(1) = 0
                        
                        grpValueIn(0) = "Mechanical-AM_0,Mechanical-AM_3,Mechanical-AM_9,0"
                        grpValueIn(1) = "LINE,LWPOLYLINE,CIRCLE"
                        
                        filterType = grpCodeIn
                        filterData = grpValueIn
                        
                        ' Select objects using Crossing Polygon
                        ssetObj_Inside.SelectByPolygon acSelectionSetCrossingPolygon, bbox, filterType, filterData
                        
                        If ssetObj_Inside.Count > 0 Then
                            For Each inside_PolyObj In ssetObj_Inside
                                
                                If TypeOf inside_PolyObj Is AcadLWPolyline Then
                                    If inside_PolyObj.Layer = "Mechanical-AM_0" Or inside_PolyObj.Layer = "0" Then        ' Select web plate
                                        beamWebPlate_Col.Add inside_PolyObj
                                    ElseIf inside_PolyObj.Layer = "Mechanical-AM_3" Then
                                        beamWebPlate_Col.Add inside_PolyObj
                                    End If
                                ElseIf TypeOf inside_PolyObj Is AcadLine Then
                                    If inside_PolyObj.Layer = "Mechanical-AM_0" Then      ' Select web plate
                                        beamWebPlate_Col.Add inside_PolyObj
                                    ElseIf inside_PolyObj.Layer = "Mechanical-AM_3" Then
                                        beamWebPlate_Col.Add inside_PolyObj
                                    End If
                                ElseIf TypeOf inside_PolyObj Is AcadCircle Then
                                    If inside_PolyObj.Layer = "Mechanical-AM_9" Then      ' Select outer circle of lashing hole
                                        lashingOuterHole_Col.Add inside_PolyObj
                                    End If
                                End If
                            Next inside_PolyObj
                        End If ' End ssetObj_Inside > 0
                        
                        If isAutoMode = False Then
                            Set ssetObj_Inside = Nothing
                            Set beamWebPlate_Col = New Collection
                            Set ssetObj_Inside = SelectStructuresByExample_Helper(bbox)
                            If Not ssetObj_Inside Is Nothing Then
                                If ssetObj_Inside.Count > 0 Then
                                    For Each inside_PolyObj In ssetObj_Inside
                                        If TypeOf inside_PolyObj Is AcadLWPolyline Or TypeOf inside_PolyObj Is AcadLine Then
                                            beamWebPlate_Col.Add inside_PolyObj
                                        End If
                                    Next inside_PolyObj
                                End If
                            End If
                        End If

                End If ' End Area Check
            End If ' End TypeOf LWPoly
            
            countpoly = countpoly + 1
            irow = irow + 1
        Next LWPoly
        
        ' Report if no valid area found
        If areaCheck = False Then
             ThisDrawing.Utility.prompt vbCrLf & "Selected objects are too small (< 20m^2). Skipped."
             Exit Sub
        End If
        
    Else
        ThisDrawing.Utility.prompt vbCrLf & "No Polyline selected!"
        Exit Sub
    End If
    
    '*******************************************************************************
    '******************* CHECK LASHING HOLE INTERFERENCE ***************************
    '*******************************************************************************
    
    Dim itemLashing As AcadCircle
    Dim itemWeb As AcadEntity
    Dim intersectPt As Variant
    Dim intersecStatus As Boolean
    Dim IntersectCount As Integer
    IntersectCount = 0
    Dim collisionHoleCount As Integer
    collisionHoleCount = 0
    Dim dblX As Double, dblY As Double, dblZ As Double, dblRotation As Double
    dblX = 1: dblY = 1: dblZ = 1: dblRotation = 0
    
    Dim midPt(0 To 2) As Double
    Dim centerLashing(0 To 2) As Double
    Dim distance As Double
    
    ' --- Input Tolerance with Error Handling ---
    Dim TOLERANCE As Double
    TOLERANCE = 0.0001

    ' -------------------------------------------
    For Each itemLashing In lashingOuterHole_Col
        For Each itemWeb In beamWebPlate_Col
            
            intersectPt = itemLashing.IntersectWith(itemWeb, acExtendNone)
            
            Dim uBoundPt As Long
            On Error Resume Next
            uBoundPt = -1
            uBoundPt = UBound(intersectPt)
            On Error GoTo 0
            
            If uBoundPt > 5 Then
                Set objBlock_Mark = ThisDrawing.ModelSpace.InsertBlock(itemLashing.Center, strBlockName, dblX, dblY, dblZ, dblRotation)
                objBlock_Mark.Layer = "Mechanical-AM_9"
                
                intersecStatus = False
                IntersectCount = IntersectCount + 1
                itemLashing.Highlight True
                
            ElseIf uBoundPt = 5 Then
                midPt(0) = (intersectPt(0) + intersectPt(3)) / 2
                midPt(1) = (intersectPt(1) + intersectPt(4)) / 2
                midPt(2) = 0
                
                centerLashing(0) = itemLashing.Center(0)
                centerLashing(1) = itemLashing.Center(1)
                centerLashing(2) = 0
                
                distance = DistanceBetweenPoints(midPt, centerLashing)
                
                If distance <= (itemLashing.Radius - TOLERANCE) Then
                    Set objBlock_Mark = ThisDrawing.ModelSpace.InsertBlock(itemLashing.Center, strBlockName, dblX, dblY, dblZ, dblRotation)
                    objBlock_Mark.Layer = "Mechanical-AM_9"
                    
                    intersecStatus = False
                    IntersectCount = IntersectCount + 1
                    itemLashing.Highlight True
                End If
                
            End If
        Next itemWeb
    Next itemLashing
 

    
    
    ' Report results
    If IntersectCount = 0 Then
        ThisDrawing.Utility.prompt vbCrLf & "No intersection between the lashing hole and structures!"
    Else
        ThisDrawing.Utility.prompt vbCrLf & "Found " & IntersectCount & " interfere positions!"
    End If
    
    Set ssetObj = Nothing
    Set ssetObj_Inside = Nothing
    
End Sub

'*******************************************************************************
' HELPER FUNCTIONS
'*******************************************************************************

Public Sub DbxCopyBlock(strBlockName As String, strPath As String)
    Dim objBlock As acadBlock
    Dim colBlocks As AcadBlocks
    Dim objArray(0) As Object
    Dim ACDbx As Object
    
    Set ACDbx = GetAcDbxDoc()
    ACDbx.Open strPath
    Set colBlocks = ACDbx.Blocks
    
    ' Find appropriate block in container file's Blocks Collection
    Set objBlock = colBlocks.Item(strBlockName)
    Set objArray(0) = objBlock ' Create object array as required by the CopyObjects Method
    
    ' Copy to current drawing's Blocks Collection
    ACDbx.CopyObjects objArray, ThisDrawing.Blocks
    
    Set ACDbx = Nothing
End Sub

Public Function GetAcDbxDoc() As Object
    Dim strAcadVersion As String
    With ThisDrawing.Application
        strAcadVersion = Mid(.Version, 1, 2)
        If CInt(strAcadVersion) < 16 Then
            Set GetAcDbxDoc = .GetInterfaceObject("ObjectDBX.AxDbDocument")
        Else
            Set GetAcDbxDoc = .GetInterfaceObject("ObjectDBX.AxDbDocument." & strAcadVersion)
        End If
    End With
End Function

Attribute VB_Name = "mod_MainLashingHole_V3"
Option Explicit

' ==========================================================================================
'  PART 1: GLOBAL VARIABLE DECLARATION, DATA STRUCTURES & MAIN CONTROLLER
' ==========================================================================================

' === MODULE CONSTANTS ===
Private Const DEFAULT_EPSILON As Double = 0.000001
Private Const MIN_DIST_FACTOR_AFTER_RETREAT As Double = 0.25
Private Const RETREAT_STEP_MM As Double = 5
Private Const TEMP_COLLISION_CHECK_LAYER As String = "TEMP_COLLISION_CHECK_LAYER"
Private Const DEFAULT_COLLISION_RATIO_THRESHOLD As Double = 5#
Private Const MAX_POINT_GENERATION_ITERATIONS_PER_LINE As Long = 100
Private Const MIN_EDGE_DISTANCE_FOR_GAP As Double = 200#
Private Const LOCAL_ADJUST_DIM_OFFSET As Double = 150#
Private Const DEFAULT_STD_MAX_RETREAT_ADDON As Double = 20
Private Const ADJACENT_STRUCTURE_FILTER_RATIO As Double = 300#

Public Const targetDimscale As Double = 25#

' === CUSTOM DATA TYPES (PUBLIC) ===
Public Type SimpleCollisionResult
    CollisionOccurred As Boolean
    IsPrimarilyVerticalHit As Boolean
    IsPrimarilyHorizontalHit As Boolean
    IsDiagonalOrComplex As Boolean
    DeltaXBetweenFirstTwo As Double
    DeltaYBetweenFirstTwo As Double
End Type

Sub CFS_CreateLashingHole()
    ' // Form & Input Variable Declaration
    Dim frmInput As Object
    Dim spacingX As Double, spacingY As Double
    Dim offsetX As Double, offsetY As Double
    Dim holeDiameter As Double
    Dim clearanceRadius As Double
    Dim ActionType As String
    
    ' // [NEW] Variables for Auto Mode, Adjacent Check & Panel Name, P1 Location
    Dim isAutoMode As Boolean
    Dim bRunCheckAdjacent As Boolean
    Dim sInputPanelName As String
    Dim sP1LocationMode As String ' <--- New variable
      
    ' // Basic CAD Variable Declaration
    Dim boundaryPline As AcadLWPolyline
    Dim p1 As Variant, p2 As Variant
    
    ' ... (Collection/SelectionSets declarations kept as is) ...
    Dim generatedPoints As Collection
    Dim createdInnerCircles As Collection, createdOuterCircles As Collection
    Dim initialDimensions As Collection, locallyAdjustedDimensions As Collection
    Dim phase3Dimensions As Collection
    Set phase3Dimensions = New Collection
    Dim structuresSS As AcadSelectionSet
    Dim tempKeepOutLines As Collection
    Dim startPointOption As String, userInputStr As String
    
    Dim bbox() As Double

    ' ... (Geometry variables kept as is) ...
    Dim x_p1 As Double, y_p1 As Double, x_p2 As Double, y_p2 As Double
    Dim rect_minX As Double, rect_maxX As Double, rect_minY As Double, rect_maxY As Double
    Dim actualCenterX As Double, actualCenterY As Double
    Dim B_abs_minX As Double, B_abs_maxX As Double, B_abs_minY As Double, B_abs_maxY As Double
    Dim dirX As Integer, dirY As Integer
    Dim stdMaxRetreat As Double
    Dim sFinalBlockName As String
    Dim acadBlock As acadBlock, blockRef As AcadBlockReference
    Dim entity As Object, allEntitiesForBlock As Collection
    Dim bBlockNameOK As Boolean
    
    On Error GoTo ErrorHandler_Main
    
    Debug.Print "=== START MACRO ==="
    Set tempKeepOutLines = New Collection

    ' === Step 1: Get Input from UserForm ===
    Set frmInput = New frmLashingInput
    frmInput.show vbModal
    
    If frmInput.IsCancelled Then
        Unload frmInput: Set frmInput = Nothing
        GoTo CancelExit_Main
    End If
    
    ActionType = frmInput.ActionType
    
    ' HANDLE AUDIT BRANCH
'    If ActionType = "Audit" Then
'        Unload frmInput: Set frmInput = Nothing
'        AuditHoles_ByTwoPoints
'        GoTo CleanExit_Main
'    End If
   
    ' CONTINUE WITH CREATE
    On Error Resume Next
    spacingX = frmInput.spacingX
    spacingY = frmInput.spacingY
    offsetX = frmInput.offsetX
    offsetY = frmInput.offsetY
    holeDiameter = frmInput.holeDiameter
    clearanceRadius = frmInput.clearanceRadius
    
    ' [NEW] Get new values from Form
    isAutoMode = frmInput.IsAutomaticMode
    bRunCheckAdjacent = frmInput.IsCheckAdjacent
    sInputPanelName = frmInput.PanelName
    sP1LocationMode = frmInput.LocationMode ' <--- Get Mode P1 (PortSide/StarBoard/Center)
    
    If Err.Number <> 0 Then
        Unload frmInput: Set frmInput = Nothing
        MsgBox "Error: Invalid input values from UserForm.", vbCritical
        Err.Clear: GoTo CleanExit_Main
    End If
    On Error GoTo ErrorHandler_Main
    Unload frmInput: Set frmInput = Nothing
    
    ' Validate input values
    If holeDiameter <= 0 Or clearanceRadius <= 0 Or Abs(spacingX) < DEFAULT_EPSILON Or Abs(spacingY) < DEFAULT_EPSILON Then
        MsgBox "Hole diameter, clearance radius, and spacing must be > 0.", vbExclamation
        GoTo CleanExit_Main
    End If
    stdMaxRetreat = (2 * clearanceRadius) + DEFAULT_STD_MAX_RETREAT_ADDON
    
    ' === Step 2: Select main boundary polyline ===
    ' Use SelectBoundaryPolyline_Helper function
    Set boundaryPline = SelectBoundaryPolyline_Helper()
    If boundaryPline Is Nothing Then GoTo CleanExit_Main
    
    ' Get bounding box from vertex of the outer polyline
    bbox = GetBoundingBoxFrmPolyline(boundaryPline.Coordinates)
    
    ' Calculate absolute Min/Max of Boundary for subsequent steps
    Dim plineCoords As Variant, k As Long
    Dim tempMinX As Double, tempMaxX As Double, tempMinY As Double, tempMaxY As Double
    On Error Resume Next
    plineCoords = boundaryPline.Coordinates
    If Err.Number <> 0 Then MsgBox "Cannot get boundary coordinates.", vbCritical: GoTo CleanExit_Main
    On Error GoTo ErrorHandler_Main
    
    tempMinX = plineCoords(0): tempMaxX = plineCoords(0)
    tempMinY = plineCoords(1): tempMaxY = plineCoords(1)
    For k = 0 To UBound(plineCoords) Step 2
        If plineCoords(k) < tempMinX Then tempMinX = plineCoords(k)
        If plineCoords(k) > tempMaxX Then tempMaxX = plineCoords(k)
        If plineCoords(k + 1) < tempMinY Then tempMinY = plineCoords(k + 1)
        If plineCoords(k + 1) > tempMaxY Then tempMaxY = plineCoords(k + 1)
    Next k
    B_abs_minX = tempMinX: B_abs_maxX = tempMaxX
    B_abs_minY = tempMinY: B_abs_maxY = tempMaxY
    
    ' === Step 3: Select structures ===
    ThisDrawing.Utility.prompt vbCrLf & "Step 3: Select EXAMPLE structures for collision checking..."
    Set structuresSS = SelectStructuresByExample_Helper(bbox)
    If structuresSS Is Nothing Or structuresSS.Count = 0 Then
        MsgBox "No structures selected. Collision check skipped.", vbInformation
        Set structuresSS = Nothing
    End If

    ' === Step 3.5: Check Adjacent Panel (Automatic Check) ===
    If bRunCheckAdjacent And Not structuresSS Is Nothing Then
        Dim sUserInput As String
        On Error Resume Next
        sUserInput = ThisDrawing.Utility.GetString(1, vbCrLf & "Check adjacent Panel? (V: Vertical / H: Horizontal / N: No) [N]: ")
        If Err.Number <> 0 Then sUserInput = "N": Err.Clear
        On Error GoTo ErrorHandler_Main
        
        Select Case UCase(Trim(sUserInput))
            Case "V"
                Debug.Print "Checking Adjacent Vertical..."
                If Not AddAdjacentPanelKeepOutZones_Helper(structuresSS, B_abs_minY, B_abs_maxY, tempKeepOutLines) Then
                    MsgBox "No valid VERTICAL adjacent structures found.", vbInformation
                End If
            Case "H"
                Debug.Print "Checking Adjacent Horizontal..."
                If Not AddAdjacentPanelKeepOutZones_Horizontal_Helper(structuresSS, B_abs_minX, B_abs_maxX, tempKeepOutLines) Then
                    MsgBox "No valid HORIZONTAL adjacent structures found.", vbInformation
                End If
        End Select
    End If
    
    ' === Step 4: Define P1, P2 ===
    If isAutoMode Then
        ' [NEW] Pass sP1LocationMode parameter to Smart function
        If Not GetSmartRectangularPointsFromPolyline(boundaryPline, p1, p2, sP1LocationMode) Then
            MsgBox "Auto-detection of boundary failed. Please pick points manually.", vbExclamation
            isAutoMode = False
            If Not GetRectangularPoints(p1, p2) Then GoTo CancelExit_Main
        Else
            Debug.Print "Smart Boundary Detected (" & sP1LocationMode & "): P1(" & p1(0) & "," & p1(1) & ") - P2(" & p2(0) & "," & p2(1) & ")"
        End If
    Else
        ' Manual selection
        If Not GetRectangularPoints(p1, p2) Then
            GoTo CancelExit_Main
        End If
    End If
    
    ' === Buoc 4.1: Chon diem bat dau (Automatic Check) ===
    If isAutoMode Then
        ' [UPDATED] Theo yeu cau: Auto Mode se bat dau tu Center thay vi P1
        startPointOption = "Center"
        Debug.Print "Auto Mode: Start Point set to Center (Override P1)"
    Else
        On Error Resume Next
        userInputStr = ThisDrawing.Utility.GetString(0, vbCrLf & "Select hole generation start point (P1, P2, Center) [Center]: ")
        If Err.Number <> 0 Then userInputStr = "Center": Err.Clear
        On Error GoTo ErrorHandler_Main
        If Trim(userInputStr) = "" Then startPointOption = "Center" Else startPointOption = UCase(Trim(userInputStr))
        If startPointOption <> "P1" And startPointOption <> "P2" Then startPointOption = "Center"
    End If

    ' Gan gia tri toa do va huong
    x_p1 = p1(0): y_p1 = p1(1): x_p2 = p2(0): y_p2 = p2(1)
    
    ' Tinh toan lai Min/Max thuc te cua hinh chu nhat P1-P2 (Bat ke chieu P1->P2)
    rect_minX = MinVal(x_p1, x_p2): rect_maxX = MaxVal(x_p1, x_p2)
    rect_minY = MinVal(y_p1, y_p2): rect_maxY = MaxVal(y_p1, y_p2)
    actualCenterX = (rect_minX + rect_maxX) / 2
    actualCenterY = (rect_minY + rect_maxY) / 2
    
    ' Xac dinh huong P1->P2 de quet lo
    If Abs(x_p2 - x_p1) < DEFAULT_EPSILON Then dirX = 1 Else dirX = Sgn(x_p2 - x_p1)
    If Abs(y_p2 - y_p1) < DEFAULT_EPSILON Then dirY = 1 Else dirY = Sgn(y_p2 - y_p1)
    
    
    ' === Step 4.2: Effective Center (Automatic Check) ===
    Dim finalEffectiveCenterX As Double, finalEffectiveCenterY As Double
    Dim skipInternalCenterAdjustment As Boolean: skipInternalCenterAdjustment = False
    
    If isAutoMode Then
        finalEffectiveCenterX = actualCenterX: finalEffectiveCenterY = actualCenterY
    Else
        If startPointOption = "P1" Or startPointOption = "P2" Then
            Dim sPickManual As String
            On Error Resume Next
            sPickManual = UCase(Trim(ThisDrawing.Utility.GetString(0, vbCrLf & "Manually select effective center point? (Y/N) [N]: ")))
            If Err.Number <> 0 Then sPickManual = "N": Err.Clear
            On Error GoTo ErrorHandler_Main
    
            If sPickManual = "Y" Then
                Dim userPickedPt As Variant, bPointValid As Boolean: bPointValid = False
                Do
                    userPickedPt = ThisDrawing.Utility.GetPoint(, vbCrLf & "Select effective center point: ")
                    If IsEmpty(userPickedPt) Then
                        finalEffectiveCenterX = actualCenterX: finalEffectiveCenterY = actualCenterY
                        skipInternalCenterAdjustment = False: bPointValid = True: Exit Do
                    End If
                    If Not IsPointInsidePolyline_Helper(userPickedPt, boundaryPline, DEFAULT_EPSILON) Then
                        MsgBox "Point is outside boundary.", vbExclamation
                    Else
                        Dim collCheck As SimpleCollisionResult
                        collCheck = ClassifyFirstCollisionForPoint(userPickedPt, clearanceRadius, structuresSS, ThisDrawing, DEFAULT_COLLISION_RATIO_THRESHOLD, DEFAULT_EPSILON)
                        If collCheck.CollisionOccurred Then
                            MsgBox "Point collides.", vbExclamation
                        Else
                            finalEffectiveCenterX = userPickedPt(0): finalEffectiveCenterY = userPickedPt(1)
                            skipInternalCenterAdjustment = True: bPointValid = True
                        End If
                    End If
                Loop While Not bPointValid
            Else
                finalEffectiveCenterX = actualCenterX: finalEffectiveCenterY = actualCenterY
            End If
        Else
            finalEffectiveCenterX = actualCenterX: finalEffectiveCenterY = actualCenterY
        End If
    End If

    ' === PHASE 1: Generate Grid ===
    ThisDrawing.Utility.prompt vbCrLf & "PHASE 1: Generating initial point grid..."
    DoEvents
    Set generatedPoints = GenerateCentralPoints( _
        startPointOption, structuresSS, clearanceRadius, p1, p2, offsetX, offsetY, spacingX, spacingY, DEFAULT_EPSILON, _
        finalEffectiveCenterX, finalEffectiveCenterY, B_abs_minX, B_abs_maxX, B_abs_minY, B_abs_maxY, _
        dirX, dirY, ThisDrawing, stdMaxRetreat, boundaryPline, skipInternalCenterAdjustment)
        
    If generatedPoints Is Nothing Or generatedPoints.Count = 0 Then
        MsgBox "PHASE 1: Unable to generate points.", vbExclamation: GoTo CleanExit_Main
    End If

    Set createdInnerCircles = Nothing: Set createdOuterCircles = Nothing
    If Not DrawLashingHoleCircles(generatedPoints, holeDiameter, clearanceRadius, createdInnerCircles, createdOuterCircles) Then
        MsgBox "PHASE 1: Error drawing holes.", vbCritical: GoTo CleanExit_Main
    End If

    Set initialDimensions = AddContinuousDimensions(generatedPoints, p1, rect_minX, rect_maxX, rect_minY, rect_maxY)
    If Not structuresSS Is Nothing And Not createdOuterCircles Is Nothing Then
        CheckAndHighlightConflicts createdOuterCircles, structuresSS
    End If
    ThisDrawing.Regen acAllViewports

    ' === PHASE 2: Special Area Adjustment ===
    Do
        Dim sPerformSpecial As String
        On Error Resume Next
        sPerformSpecial = UCase(Trim(ThisDrawing.Utility.GetString(0, vbCrLf & "Perform special area adjustment? (Y/N) [N]: ")))
        If Err.Number <> 0 Then sPerformSpecial = "N": Err.Clear
        On Error GoTo ErrorHandler_Main
        
        If sPerformSpecial = "Y" Then
            Dim tempPhase3Dims As Collection
            Set tempPhase3Dims = PerformSpecialAreaAdjustment_Phase3(createdInnerCircles, createdOuterCircles, p1, p2, boundaryPline, _
                structuresSS, stdMaxRetreat, spacingX, spacingY, holeDiameter, clearanceRadius, offsetY, offsetX, _
                B_abs_minX, B_abs_maxX, B_abs_minY, B_abs_maxY)
            If Not tempPhase3Dims Is Nothing Then
                Dim dObj As Object
                For Each dObj In tempPhase3Dims: phase3Dimensions.Add dObj: Next dObj
            End If
        Else
            Exit Do
        End If
    Loop
    ThisDrawing.Regen acAllViewports

    ' === PHASE 3: Local Adjustment (Automatic Check) ===
    Dim sPerformLocal As String
    If isAutoMode Then
        sPerformLocal = "Y"
        Debug.Print "Auto Mode: Running Local Adjustment automatically."
    Else
        On Error Resume Next
        sPerformLocal = ThisDrawing.Utility.GetString(0, vbCrLf & "Perform local adjustment for colliding holes? (Y/N) [N]: ")
        If Err.Number <> 0 Then sPerformLocal = "N": Err.Clear
        On Error GoTo ErrorHandler_Main
    End If
    
    If UCase(Trim(sPerformLocal)) = "Y" Then
        Set locallyAdjustedDimensions = PerformLocalAdjustments_Phase2(createdOuterCircles, createdInnerCircles, structuresSS, ThisDrawing, clearanceRadius, DEFAULT_EPSILON, stdMaxRetreat, B_abs_minX, B_abs_maxX, B_abs_minY, B_abs_maxY, boundaryPline)
    End If
    ThisDrawing.Regen acAllViewports

    ' === BLOCK PACKING ===
    ThisDrawing.Utility.prompt vbCrLf & "BLOCK PACKING: Preparing..."
    ThisDrawing.StartUndoMark
    
    ' [UPDATED] Create block name from Panel Name entered in Form
    Dim sProposedBlockName As String
    sProposedBlockName = sInputPanelName & "_L.H" ' Syntax: PanelName_L.H
    
    bBlockNameOK = False
    
    ' Check if block already exists
    Dim blkCheck As acadBlock: Set blkCheck = Nothing
    On Error Resume Next: Set blkCheck = ThisDrawing.Blocks.Item(sProposedBlockName): On Error GoTo ErrorHandler_Main
    
    If blkCheck Is Nothing Then
        ' If not exists -> Use this name
        sFinalBlockName = sProposedBlockName
        bBlockNameOK = True
    Else
        ' If ALREADY exists -> Show InputBox to rename (fallback loop)
        MsgBox "Block name '" & sProposedBlockName & "' already exists. Please choose another name.", vbExclamation
        sFinalBlockName = ""
    End If
    
    ' Loop only runs if initial name duplicates
    Do While Not bBlockNameOK
        sInputPanelName = InputBox("Enter Panel Name (Block '" & sProposedBlockName & "' exists):", "Set Block Name", sInputPanelName & "_" & Format(Timer, "00"))
        If sInputPanelName = "" Then GoTo SkipBlockCreation_Main
        
        sProposedBlockName = sInputPanelName & "_L.H"
        Set blkCheck = Nothing
        On Error Resume Next: Set blkCheck = ThisDrawing.Blocks.Item(sProposedBlockName): On Error GoTo ErrorHandler_Main
        
        If Not blkCheck Is Nothing Then
            MsgBox "Block name still exists. Try again.", vbExclamation
        Else
            sFinalBlockName = sProposedBlockName
            bBlockNameOK = True
        End If
    Loop

    Set allEntitiesForBlock = New Collection
    CollectValidEntities allEntitiesForBlock, createdInnerCircles, "InnerCircle"
    CollectValidEntities allEntitiesForBlock, createdOuterCircles, "OuterCircle"
    CollectValidEntities allEntitiesForBlock, initialDimensions, "InitialDimension"
    CollectValidEntities allEntitiesForBlock, locallyAdjustedDimensions, "LocallyAdjustedDimension"
    
    If phase3Dimensions.Count > 0 Then
        CollectValidEntities allEntitiesForBlock, phase3Dimensions, "Phase3Dimension"
    End If

    If allEntitiesForBlock.Count > 0 Then
        Dim p1_ForBlock As Variant: p1_ForBlock = p1
        Set acadBlock = ThisDrawing.Blocks.Add(p1_ForBlock, sFinalBlockName)
        
        Dim blockEntities() As AcadEntity
        ReDim blockEntities(0 To allEntitiesForBlock.Count - 1)
        Dim i As Long: i = 0
        For Each entity In allEntitiesForBlock
            Set blockEntities(i) = entity
            i = i + 1
        Next entity

        Dim copiedObjects As Variant
        copiedObjects = ThisDrawing.Database.CopyObjects(blockEntities, acadBlock)
        
        Set blockRef = ThisDrawing.ModelSpace.InsertBlock(p1_ForBlock, sFinalBlockName, 1#, 1#, 1#, 0)
        If Not blockRef Is Nothing Then
            On Error Resume Next
            For Each entity In allEntitiesForBlock
                If Not entity Is Nothing Then entity.Delete
            Next entity
            On Error GoTo ErrorHandler_Main
            ThisDrawing.Utility.prompt ("Block '" & sFinalBlockName & "' created successfully.")
        End If
    End If
    
SkipBlockCreation_Main:
    ThisDrawing.EndUndoMark
    GoTo CleanExit_Main

CancelExit_Main:
    ThisDrawing.Utility.prompt ("Operation cancelled.")

CleanExit_Main:
    If Not tempKeepOutLines Is Nothing Then
        Dim tempObj As AcadEntity
        For Each tempObj In tempKeepOutLines
            On Error Resume Next: tempObj.Delete: On Error GoTo 0
        Next tempObj
    End If
    Dim tmpLayer As AcadLayer
    On Error Resume Next: Set tmpLayer = ThisDrawing.Layers.Item(TEMP_COLLISION_CHECK_LAYER)
    If Not tmpLayer Is Nothing Then tmpLayer.Delete
    On Error GoTo 0
    Debug.Print "=== END MACRO ==="
    Exit Sub

ErrorHandler_Main:
    ThisDrawing.Utility.prompt ("Runtime Error: " & Err.Number & " - " & Err.Description)
    On Error Resume Next: ThisDrawing.EndUndoMark
    Resume CleanExit_Main
End Sub

' ==========================================================================================
'  PART 2: CORE LOGIC & COLLISION ENGINE
'  Task: Classify collisions, check point inside polyline, math functions.
' ==========================================================================================

' === FUNCTION TO CLASSIFY COLLISION BASED ON FIRST TWO INTERSECTION POINTS (CORE LOGIC) ===
Public Function ClassifyCollisionByFirstTwoPoints( _
    ByVal circleToCheck As AcadCircle, _
    ByVal structureToCheck As AcadEntity, _
    ByVal collisionRatioThreshold As Double, _
    ByVal epsilonValue As Double _
) As SimpleCollisionResult
    Dim result As SimpleCollisionResult
    Dim conflictPoints As Variant
    Dim p1x As Double, p1y As Double, p2x As Double, p2y As Double
    Dim deltaX As Double, deltaY As Double

    ' Initialize default values
    result.CollisionOccurred = False
    result.IsPrimarilyVerticalHit = False
    result.IsPrimarilyHorizontalHit = False
    result.IsDiagonalOrComplex = False
    result.DeltaXBetweenFirstTwo = 0
    result.DeltaYBetweenFirstTwo = 0

    If circleToCheck Is Nothing Or structureToCheck Is Nothing Then Exit Function
    If collisionRatioThreshold <= 0 Then collisionRatioThreshold = DEFAULT_COLLISION_RATIO_THRESHOLD
    If epsilonValue <= 0 Then epsilonValue = DEFAULT_EPSILON

    On Error GoTo ClassifyLogicErrorHandler
    
    ' Check intersection
    conflictPoints = circleToCheck.IntersectWith(structureToCheck, acExtendNone)

    If IsArray(conflictPoints) Then
        ' Need at least 2 intersection points (6 coordinates: x1,y1,z1, x2,y2,z2) for accurate classification
        If UBound(conflictPoints) >= 5 Then
            result.CollisionOccurred = True
            p1x = conflictPoints(0): p1y = conflictPoints(1)
            p2x = conflictPoints(3): p2y = conflictPoints(4)
            deltaX = Abs(p1x - p2x): deltaY = Abs(p1y - p2y)
            result.DeltaXBetweenFirstTwo = deltaX
            result.DeltaYBetweenFirstTwo = deltaY

            ' Classify based on dx/dy ratio
            If deltaY > deltaX * collisionRatioThreshold + epsilonValue Then
                result.IsPrimarilyVerticalHit = True
                ' Debug.Print "   -> VERTICAL Collision (DeltaY=" & Format(deltaY, "0.00") & " > DeltaX=" & Format(deltaX, "0.00") & ")"
            ElseIf deltaX > deltaY * collisionRatioThreshold + epsilonValue Then
                result.IsPrimarilyHorizontalHit = True
                ' Debug.Print "   -> HORIZONTAL Collision (DeltaX=" & Format(deltaX, "0.00") & " > DeltaY=" & Format(deltaY, "0.00") & ")"
            Else
                result.IsDiagonalOrComplex = True
                ' Debug.Print "   -> DIAGONAL/COMPLEX Collision"
            End If
        ElseIf UBound(conflictPoints) >= 0 Then
            ' At least 1 intersection point (tangent or single point) -> Treat as complex
            result.CollisionOccurred = True
            result.IsDiagonalOrComplex = True
            ' Debug.Print "   -> SINGLE Collision (1 hit point)"
        End If
    End If
    
    ClassifyCollisionByFirstTwoPoints = result
    Exit Function

ClassifyLogicErrorHandler:
    ' If error, assume collision to be safe
    Debug.Print "*** ERROR in ClassifyCollisionByFirstTwoPoints: " & Err.Description & " ***"
    result.CollisionOccurred = True
    result.IsDiagonalOrComplex = True
    ClassifyCollisionByFirstTwoPoints = result
End Function

' === COLLISION CLASSIFICATION FUNCTION (WRAPPER FOR 1 POINT) ===
Public Function ClassifyFirstCollisionForPoint( _
    ByVal pointCoords As Variant, _
    ByVal checkRadius As Double, _
    ByVal structures As AcadSelectionSet, _
    ByVal currentDrawing As AcadDocument, _
    ByVal collisionRatioThreshold As Double, _
    ByVal epsilonValue As Double _
) As SimpleCollisionResult
    Dim result As SimpleCollisionResult
    Dim tempCircle As AcadCircle
    Dim centerPt(0 To 2) As Double
    Dim structure As AcadEntity
    Dim targetLayer As AcadLayer
    Dim originalLayer As AcadLayer
    
    result.CollisionOccurred = False
    result.IsPrimarilyVerticalHit = False
    result.IsPrimarilyHorizontalHit = False
    result.IsDiagonalOrComplex = False

    If structures Is Nothing Or structures.Count = 0 Then
        ClassifyFirstCollisionForPoint = result
        Exit Function
    End If
    
    centerPt(0) = pointCoords(0): centerPt(1) = pointCoords(1): centerPt(2) = 0
    If epsilonValue <= 0 Then epsilonValue = DEFAULT_EPSILON

    On Error GoTo ClassifyWrapperError

    ' Save current layer
    Set originalLayer = currentDrawing.ActiveLayer

    ' Create or get temporary layer to draw check circle
    On Error Resume Next
    Set targetLayer = currentDrawing.Layers.Item(TEMP_COLLISION_CHECK_LAYER)
    If targetLayer Is Nothing Then
        On Error GoTo ClassifyWrapperError
        Set targetLayer = currentDrawing.Layers.Add(TEMP_COLLISION_CHECK_LAYER)
        targetLayer.color = acMagenta
        targetLayer.Plottable = False
    Else
        If Not targetLayer.LayerOn Then targetLayer.LayerOn = True
        If targetLayer.Freeze Then targetLayer.Freeze = False
        If targetLayer.Lock Then targetLayer.Lock = False
    End If
    currentDrawing.ActiveLayer = targetLayer
    
    ' Draw virtual circle
    Set tempCircle = currentDrawing.ModelSpace.AddCircle(centerPt, checkRadius)

    ' Iterate through structures to check
    For Each structure In structures
        If Not structure Is Nothing Then
            result = ClassifyCollisionByFirstTwoPoints(tempCircle, structure, collisionRatioThreshold, epsilonValue)
            If result.CollisionOccurred Then
                ' Debug.Print "Collision detected at (" & Format(centerPt(0), "0.0") & "," & Format(centerPt(1), "0.0") & ") with Handle: " & structure.Handle
                Exit For ' Stop at first collision to save time
            End If
        End If
    Next structure

FinallyDeleteTempCircle_Wrapper:
    ' Clean up virtual circle
    If Not tempCircle Is Nothing Then
        On Error Resume Next: tempCircle.Delete: Set tempCircle = Nothing: On Error GoTo 0
    End If
    
    ' Restore old layer
    If Not originalLayer Is Nothing Then
        On Error Resume Next
        currentDrawing.ActiveLayer = originalLayer
        If Err.Number <> 0 Then currentDrawing.ActiveLayer = currentDrawing.Layers.Item("0")
        On Error GoTo 0
    End If
    
    ClassifyFirstCollisionForPoint = result
    Exit Function

ClassifyWrapperError:
    Debug.Print "*** ERROR in ClassifyFirstCollisionForPoint: " & Err.Description & " ***"
    result.CollisionOccurred = True ' Default to collision if system error
    result.IsDiagonalOrComplex = True
    Resume FinallyDeleteTempCircle_Wrapper
End Function

' === FUNCTION TO CHECK IF POINT IS INSIDE POLYLINE (RAY CASTING) ===
' [UPDATED] Removed "If Not pline.Closed Then Exit Function" to allow Open Polyline
Private Function IsPointInsidePolyline_Helper(ByVal pointToCheck As Variant, ByVal pline As AcadLWPolyline, ByVal epsilonValue As Double) As Boolean
    Dim coords As Variant
    Dim nvert As Long
    Dim idx As Long, jdx As Long
    Dim c As Boolean: c = False ' Number of intersections
    Dim testx As Double, testy As Double
    
    On Error GoTo IsPointInsideErrorHandler
    IsPointInsidePolyline_Helper = False
    If epsilonValue <= 0 Then epsilonValue = 0.000001 ' Default Epsilon

    If pline Is Nothing Then Exit Function
    
    ' [ÐÃ XÓA] Dòng ki?m tra Closed d? cho phép Polyline h? ch?y ti?p
    ' If Not pline.Closed Then Exit Function
    
    coords = pline.Coordinates
    If Not IsArray(coords) Or UBound(coords) < 1 Then Exit Function
    
    nvert = (UBound(coords) + 1) / 2
    testx = pointToCheck(0)
    testy = pointToCheck(1)
    
    ' Thu?t toán Ray Casting t? d?ng n?i di?m cu?i v? di?m d?u
    jdx = nvert - 1
    
    For idx = 0 To nvert - 1
        Dim pXi As Double, pYi As Double, pXj As Double, pYj As Double
        pXi = coords(idx * 2)
        pYi = coords(idx * 2 + 1)
        pXj = coords(jdx * 2)
        pYj = coords(jdx * 2 + 1)
        
        ' Check if point coincides with vertex or lies on edge (rough check)
        If Abs(pXi - testx) < epsilonValue And Abs(pYi - testy) < epsilonValue Then
            IsPointInsidePolyline_Helper = True: Exit Function
        End If
        If Abs(pYi - testy) < epsilonValue And Abs(pYj - testy) < epsilonValue Then ' Horizontal edge
            If (testx >= MinVal(pXi, pXj) - epsilonValue And testx <= MaxVal(pXi, pXj) + epsilonValue) Then
                IsPointInsidePolyline_Helper = True: Exit Function
            End If
        End If
        If Abs(pXi - testx) < epsilonValue And Abs(pXj - testx) < epsilonValue Then ' Vertical edge
            If (testy >= MinVal(pYi, pYj) - epsilonValue And testy <= MaxVal(pYi, pYj) + epsilonValue) Then
                IsPointInsidePolyline_Helper = True: Exit Function
            End If
        End If

        ' Ray Casting Algorithm (Horizontal ray to the left)
        If ((pYi > testy) <> (pYj > testy)) Then
            ' Avoid division by zero
            If Abs(pYj - pYi) > epsilonValue Then
                Dim intersectX As Double
                intersectX = (pXj - pXi) * (testy - pYi) / (pYj - pYi) + pXi
                If testx < intersectX Then c = Not c
            End If
        End If
        jdx = idx
    Next idx
    
    IsPointInsidePolyline_Helper = c
    Exit Function

IsPointInsideErrorHandler:
    Debug.Print "*** ERROR in IsPointInsidePolyline_Helper: " & Err.Description & " ***"
    IsPointInsidePolyline_Helper = False
End Function

' === MIN/MAX HELPER FUNCTIONS (Gi? nguyên) ===
Private Function MinVal(ByVal val1 As Double, ByVal val2 As Double) As Double
    If val1 < val2 Then MinVal = val1 Else MinVal = val2
End Function

Private Function MaxVal(ByVal val1 As Double, ByVal val2 As Double) As Double
    If val1 > val2 Then MaxVal = val1 Else MaxVal = val2
End Function

' ==========================================================================================
'  PART 3: PHASE 1 - GRID GENERATION
'  Task: Create initial point grid, calculate rows/cols, draw circles.
' ==========================================================================================

' === FUNCTION TO GENERATE POINTS FOR CENTRAL ROW AND COLUMN ===
Private Function GenerateCentralPoints( _
    ByVal startPointOption As String, ByVal structuresSS As AcadSelectionSet, ByVal clearanceRadius As Double, _
    ByVal p1 As Variant, ByVal p2 As Variant, _
    ByVal offsetX_fromForm As Double, ByVal offsetY_fromForm As Double, ByVal spacingX As Double, ByVal spacingY As Double, _
    ByVal epsilonValue As Double, ByVal actualCenterX_fromCaller As Double, ByVal actualCenterY_fromCaller As Double, _
    ByVal B_abs_minX As Double, ByVal B_abs_maxX As Double, ByVal B_abs_minY As Double, ByVal B_abs_maxY As Double, _
    ByVal dirX As Integer, ByVal dirY As Integer, ByVal currentDrawing As AcadDocument, _
    ByVal standardMaxRetreat As Double, ByVal mainBoundaryPline As AcadLWPolyline, _
    Optional ByVal skipInitialAdjustment As Boolean = False _
) As Collection
    
    On Error GoTo GenerateCentralPointsErrorHandler
    If epsilonValue <= 0 Then epsilonValue = DEFAULT_EPSILON

    Dim dictStandardPoints As Object: Set dictStandardPoints = CreateObject("Scripting.Dictionary")
    Dim finalGridPointsDict As Object
    Dim outputPoints As Collection
    Set outputPoints = New Collection
    Set GenerateCentralPoints = outputPoints

    Dim initialStartAnchor(0 To 2) As Double
    Dim initialEndAnchor(0 To 2) As Double
    Dim calculatedMaxRetreatForStartAnchor As Double

    Dim effectiveRowY As Double
    Dim effectiveColX As Double
    Dim seedForRow(0 To 2) As Double
    Dim seedForCol(0 To 2) As Double
    
    Dim adjustedEffectiveCenterX As Double, adjustedEffectiveCenterY As Double

    ' --- Adjust effective center ---
    If skipInitialAdjustment Then
        adjustedEffectiveCenterX = actualCenterX_fromCaller
        adjustedEffectiveCenterY = actualCenterY_fromCaller
        Debug.Print "GenerateCentralPoints: Using available effective center: (" & Format(adjustedEffectiveCenterX, "0.00") & "," & Format(adjustedEffectiveCenterY, "0.00") & ")"
    Else
        Dim effectiveCenterSeedPt(0 To 2) As Double
        effectiveCenterSeedPt(0) = actualCenterX_fromCaller
        effectiveCenterSeedPt(1) = actualCenterY_fromCaller
        effectiveCenterSeedPt(2) = 0

        ' Call 8-direction center adjustment function (From Part 4)
        If Not AdjustInitialCenter8Dir(effectiveCenterSeedPt, clearanceRadius, structuresSS, currentDrawing, epsilonValue, B_abs_minX, B_abs_maxX, B_abs_minY, B_abs_maxY, mainBoundaryPline) Then
            MsgBox "Cannot find collision-free effective center point. Macro will stop.", vbExclamation
            Exit Function
        End If

        adjustedEffectiveCenterX = effectiveCenterSeedPt(0)
        adjustedEffectiveCenterY = effectiveCenterSeedPt(1)
        Debug.Print "GenerateCentralPoints: Effective center AFTER adjustment: (" & Format(adjustedEffectiveCenterX, "0.00") & "," & Format(adjustedEffectiveCenterY, "0.00") & ")"
    End If

    effectiveColX = adjustedEffectiveCenterX
    effectiveRowY = adjustedEffectiveCenterY

    ' --- Create base rows/cols based on selection ---
    Select Case startPointOption
        Case "Center"
            AddPointToDictIfNotExist dictStandardPoints, adjustedEffectiveCenterX, adjustedEffectiveCenterY, epsilonValue
            
            seedForCol(0) = adjustedEffectiveCenterX: seedForCol(1) = adjustedEffectiveCenterY: seedForCol(2) = 0
            seedForRow(0) = adjustedEffectiveCenterX: seedForRow(1) = adjustedEffectiveCenterY: seedForRow(2) = 0
            
            calculatedMaxRetreatForStartAnchor = standardMaxRetreat

            ' Col Up
            initialEndAnchor(0) = effectiveColX: initialEndAnchor(1) = B_abs_maxY - offsetY_fromForm: initialEndAnchor(2) = 0
            GenerateLineOfPoints dictStandardPoints, seedForCol, initialEndAnchor, spacingY, 1, False, effectiveColX, clearanceRadius, structuresSS, currentDrawing, epsilonValue, MIN_EDGE_DISTANCE_FOR_GAP, p1, p2, B_abs_minY, B_abs_maxY, "CenterColUp", calculatedMaxRetreatForStartAnchor, actualCenterY_fromCaller, True, True, standardMaxRetreat

            ' Col Down
            initialEndAnchor(0) = effectiveColX: initialEndAnchor(1) = B_abs_minY + offsetY_fromForm: initialEndAnchor(2) = 0
            GenerateLineOfPoints dictStandardPoints, seedForCol, initialEndAnchor, spacingY, -1, False, effectiveColX, clearanceRadius, structuresSS, currentDrawing, epsilonValue, MIN_EDGE_DISTANCE_FOR_GAP, p1, p2, B_abs_minY, B_abs_maxY, "CenterColDown", calculatedMaxRetreatForStartAnchor, actualCenterY_fromCaller, True, True, standardMaxRetreat

            ' Row Right
            initialEndAnchor(0) = B_abs_maxX - offsetX_fromForm: initialEndAnchor(1) = effectiveRowY: initialEndAnchor(2) = 0
            GenerateLineOfPoints dictStandardPoints, seedForRow, initialEndAnchor, spacingX, 1, True, effectiveRowY, clearanceRadius, structuresSS, currentDrawing, epsilonValue, MIN_EDGE_DISTANCE_FOR_GAP, p1, p2, B_abs_minX, B_abs_maxX, "CenterRowRight", calculatedMaxRetreatForStartAnchor, actualCenterX_fromCaller, True, True, standardMaxRetreat

            ' Row Left
            initialEndAnchor(0) = B_abs_minX + offsetX_fromForm: initialEndAnchor(1) = effectiveRowY: initialEndAnchor(2) = 0
            GenerateLineOfPoints dictStandardPoints, seedForRow, initialEndAnchor, spacingX, -1, True, effectiveRowY, clearanceRadius, structuresSS, currentDrawing, epsilonValue, MIN_EDGE_DISTANCE_FOR_GAP, p1, p2, B_abs_minX, B_abs_maxX, "CenterRowLeft", calculatedMaxRetreatForStartAnchor, actualCenterX_fromCaller, True, True, standardMaxRetreat
            
        Case "P1"
            ' P1 Col
            initialStartAnchor(0) = effectiveColX
            initialStartAnchor(1) = p1(1) + dirY * offsetY_fromForm
            initialStartAnchor(2) = 0
            initialEndAnchor(0) = effectiveColX
            initialEndAnchor(1) = p2(1) - dirY * offsetY_fromForm
            initialEndAnchor(2) = 0
            GenerateLineOfPoints dictStandardPoints, initialStartAnchor, initialEndAnchor, spacingY, dirY, False, effectiveColX, clearanceRadius, structuresSS, currentDrawing, epsilonValue, MIN_EDGE_DISTANCE_FOR_GAP, p1, p2, B_abs_minY, B_abs_maxY, "P1Col", standardMaxRetreat, p1(1), False, False, standardMaxRetreat

            ' P1 Row
            initialStartAnchor(0) = p1(0) + dirX * offsetX_fromForm
            initialStartAnchor(1) = effectiveRowY
            initialStartAnchor(2) = 0
            initialEndAnchor(0) = p2(0) - dirX * offsetX_fromForm
            initialEndAnchor(1) = effectiveRowY
            initialEndAnchor(2) = 0
            GenerateLineOfPoints dictStandardPoints, initialStartAnchor, initialEndAnchor, spacingX, dirX, True, effectiveRowY, clearanceRadius, structuresSS, currentDrawing, epsilonValue, MIN_EDGE_DISTANCE_FOR_GAP, p1, p2, B_abs_minX, B_abs_maxX, "P1Row", standardMaxRetreat, p1(0), False, False, standardMaxRetreat

        Case "P2"
            ' P2 Col
            initialStartAnchor(0) = effectiveColX
            initialStartAnchor(1) = p2(1) - dirY * offsetY_fromForm
            initialStartAnchor(2) = 0
            initialEndAnchor(0) = effectiveColX
            initialEndAnchor(1) = p1(1) + dirY * offsetY_fromForm
            initialEndAnchor(2) = 0
            GenerateLineOfPoints dictStandardPoints, initialStartAnchor, initialEndAnchor, spacingY, -dirY, False, effectiveColX, clearanceRadius, structuresSS, currentDrawing, epsilonValue, MIN_EDGE_DISTANCE_FOR_GAP, p1, p2, B_abs_minY, B_abs_maxY, "P2Col", standardMaxRetreat, p2(1), False, False, standardMaxRetreat

            ' P2 Row
            initialStartAnchor(0) = p2(0) - dirX * offsetX_fromForm
            initialStartAnchor(1) = effectiveRowY
            initialStartAnchor(2) = 0
            initialEndAnchor(0) = p1(0) + dirX * offsetX_fromForm
            initialEndAnchor(1) = effectiveRowY
            initialEndAnchor(2) = 0
            GenerateLineOfPoints dictStandardPoints, initialStartAnchor, initialEndAnchor, spacingX, -dirX, True, effectiveRowY, clearanceRadius, structuresSS, currentDrawing, epsilonValue, MIN_EDGE_DISTANCE_FOR_GAP, p1, p2, B_abs_minX, B_abs_maxX, "P2Row", standardMaxRetreat, p2(0), False, False, standardMaxRetreat
    End Select

    ' --- Aggregate and create grid ---
    Dim allGeneratedUniqueXCoords As Object: Set allGeneratedUniqueXCoords = CreateObject("Scripting.Dictionary")
    Dim allGeneratedUniqueYCoords As Object: Set allGeneratedUniqueYCoords = CreateObject("Scripting.Dictionary")
    Dim xCoordsOnEffectiveRowAxis As Object
    Dim yCoordsOnEffectiveColAxis As Object

    If dictStandardPoints.Count = 0 Then Exit Function

    If startPointOption = "P1" Or startPointOption = "P2" Then
        Set xCoordsOnEffectiveRowAxis = CreateObject("Scripting.Dictionary")
        Set yCoordsOnEffectiveColAxis = CreateObject("Scripting.Dictionary")
    End If

    Dim ptItem As Variant, xKey As String, yKey As String
    Dim currentXVal As Double, currentYVal As Double

    ' Extract unique X and Y coordinates from points on base axes
    For Each ptItem In dictStandardPoints.Items
        currentXVal = ptItem(0): currentYVal = ptItem(1)
        xKey = GetCoordKey(currentXVal, epsilonValue)
        yKey = GetCoordKey(currentYVal, epsilonValue)

        If Not allGeneratedUniqueXCoords.Exists(xKey) Then allGeneratedUniqueXCoords.Add xKey, currentXVal
        If Not allGeneratedUniqueYCoords.Exists(yKey) Then allGeneratedUniqueYCoords.Add yKey, currentYVal

        If startPointOption = "P1" Or startPointOption = "P2" Then
            If Abs(currentYVal - effectiveRowY) < epsilonValue Then
                If Not xCoordsOnEffectiveRowAxis.Exists(xKey) Then xCoordsOnEffectiveRowAxis.Add xKey, currentXVal
            End If
            If Abs(currentXVal - effectiveColX) < epsilonValue Then
                If Not yCoordsOnEffectiveColAxis.Exists(yKey) Then yCoordsOnEffectiveColAxis.Add yKey, currentYVal
            End If
        End If
    Next ptItem

    Dim finalXCoordsToGrid As Object: Set finalXCoordsToGrid = CreateObject("Scripting.Dictionary")
    Dim finalYCoordsToGrid As Object: Set finalYCoordsToGrid = CreateObject("Scripting.Dictionary")
    Dim coordKey As Variant

    If startPointOption = "P1" Or startPointOption = "P2" Then
        For Each coordKey In xCoordsOnEffectiveRowAxis.Keys: finalXCoordsToGrid.Add coordKey, xCoordsOnEffectiveRowAxis(coordKey): Next
        For Each coordKey In yCoordsOnEffectiveColAxis.Keys: finalYCoordsToGrid.Add coordKey, yCoordsOnEffectiveColAxis(coordKey): Next
    Else
        For Each coordKey In allGeneratedUniqueXCoords.Keys: finalXCoordsToGrid.Add coordKey, allGeneratedUniqueXCoords(coordKey): Next
        For Each coordKey In allGeneratedUniqueYCoords.Keys: finalYCoordsToGrid.Add coordKey, allGeneratedUniqueYCoords(coordKey): Next
    End If
    
    If finalXCoordsToGrid.Count = 0 Or finalYCoordsToGrid.Count = 0 Then Exit Function
    
    ' Create intersection grid points
    Set finalGridPointsDict = CreateObject("Scripting.Dictionary")
    Dim gridX As Variant, gridY As Variant
    Dim finalPt(0 To 2) As Double
    
    For Each gridX In finalXCoordsToGrid.Items
        For Each gridY In finalYCoordsToGrid.Items
            finalPt(0) = gridX: finalPt(1) = gridY: finalPt(2) = 0
            ' Check if inside boundary
            If IsPointInsidePolyline_Helper(finalPt, mainBoundaryPline, epsilonValue) Then
                AddPointToDictIfNotExist finalGridPointsDict, finalPt(0), finalPt(1), epsilonValue
            End If
        Next gridY
    Next gridX
    
    For Each coordKey In finalGridPointsDict.Keys
        outputPoints.Add finalGridPointsDict(coordKey)
    Next coordKey

    Debug.Print "GenerateCentralPoints: Total Grid Points Created: " & outputPoints.Count
    Set GenerateCentralPoints = outputPoints
    Exit Function

GenerateCentralPointsErrorHandler:
    Debug.Print "*** ERROR in GenerateCentralPoints: " & Err.Description & " ***"
    Set GenerateCentralPoints = New Collection
End Function

' === HELPER FUNCTION TO GENERATE A LINE OF POINTS (Preserves Gap & Li-1 Logic) ===
Private Sub GenerateLineOfPoints( _
    ByRef ioDictPoints As Object, _
    ByVal vInitialStartAnchor As Variant, ByVal vInitialEndAnchor As Variant, _
    ByVal dblSpacing As Double, ByVal intGenDirOriginal As Integer, ByVal blnAxisIsX As Boolean, _
    ByVal dblFixedCoordVal As Double, ByVal dblClearanceRadius As Double, _
    ByVal collStructuresSS As AcadSelectionSet, ByVal objCurrentDrawing As AcadDocument, _
    ByVal dblEpsilonValue As Double, ByVal dblMinEdgeDistForGap As Double, _
    ByVal vP1 As Variant, ByVal vP2 As Variant, _
    ByVal dblBoundaryMin As Double, ByVal dblBoundaryMax As Double, _
    ByVal strDebugPrefix As String, ByVal dblMaxRetreatForStartAnchor As Double, _
    ByVal dblPrevCoordForStartAnchorAdj As Double, _
    ByVal blnAdjustStartAnchor As Boolean, ByVal blnAdjustEndAnchor As Boolean, _
    ByVal standardMaxRetreatPassedAsParam As Double)
    
    On Error GoTo GenerateLineErrorHandler
    If dblEpsilonValue <= 0 Then dblEpsilonValue = DEFAULT_EPSILON

    Dim startAnchor(0 To 2) As Double, endAnchor(0 To 2) As Double
    Dim currentPt(0 To 2) As Double, candidatePt(0 To 2) As Double
    Dim Li_minus_1(0 To 2) As Double, Li(0 To 2) As Double ' Li is endAnchor
    Dim repositioned_Lminus1(0 To 2) As Double

    Dim varyingCoordIdx As Integer, fixedCoordIdx As Integer
    If blnAxisIsX Then varyingCoordIdx = 0: fixedCoordIdx = 1 Else varyingCoordIdx = 1: fixedCoordIdx = 0

    Dim collInfo As SimpleCollisionResult
    Dim adjusted As Boolean
    Dim loopCounter As Long
    Dim dblDistanceToLi As Double
    Dim tempAdjustedCoord As Double
    Dim intGenDir As Integer: intGenDir = intGenDirOriginal
    Dim currentMaxRetreat As Double
    Dim collisionNeedsAdjustment As Boolean
    
    If intGenDir = 0 Then ' Fallback logic
        If vInitialStartAnchor(varyingCoordIdx) < vInitialEndAnchor(varyingCoordIdx) Then intGenDir = 1 Else intGenDir = -1
    End If

    ' --- Check case where Start and End are too close ---
    If Abs(vInitialStartAnchor(varyingCoordIdx) - vInitialEndAnchor(varyingCoordIdx)) < dblSpacing / 2 Then
        startAnchor(0) = vInitialStartAnchor(0): startAnchor(1) = vInitialStartAnchor(1): startAnchor(2) = vInitialStartAnchor(2)
        If (startAnchor(varyingCoordIdx) > dblBoundaryMax - dblEpsilonValue And intGenDir = 1) Or _
           (startAnchor(varyingCoordIdx) < dblBoundaryMin + dblEpsilonValue And intGenDir = -1) Then Exit Sub
        
        If blnAdjustStartAnchor Then
            collInfo = ClassifyFirstCollisionForPoint(startAnchor, dblClearanceRadius, collStructuresSS, objCurrentDrawing, DEFAULT_COLLISION_RATIO_THRESHOLD, dblEpsilonValue)
            If collInfo.CollisionOccurred Then
                tempAdjustedCoord = startAnchor(varyingCoordIdx)
                If blnAxisIsX Then
                    adjusted = AdjustPointHorizontal(tempAdjustedCoord, startAnchor(fixedCoordIdx), intGenDir, dblClearanceRadius, collStructuresSS, dblMaxRetreatForStartAnchor, dblPrevCoordForStartAnchorAdj, dblSpacing, dblBoundaryMin, dblBoundaryMax, dblEpsilonValue, objCurrentDrawing, collInfo, vP1, vP2, True)
                Else
                    adjusted = AdjustPointVertical(tempAdjustedCoord, startAnchor(fixedCoordIdx), intGenDir, dblClearanceRadius, collStructuresSS, dblMaxRetreatForStartAnchor, dblPrevCoordForStartAnchorAdj, dblSpacing, dblBoundaryMin, dblBoundaryMax, dblEpsilonValue, objCurrentDrawing, collInfo, vP1, vP2, True)
                End If
                If adjusted Then startAnchor(varyingCoordIdx) = tempAdjustedCoord Else Exit Sub
            End If
        End If
        
        If (startAnchor(varyingCoordIdx) > dblBoundaryMax - dblEpsilonValue And intGenDir = 1) Or _
           (startAnchor(varyingCoordIdx) < dblBoundaryMin + dblEpsilonValue And intGenDir = -1) Then Exit Sub
        
        AddPointToDictIfNotExist ioDictPoints, startAnchor(0), startAnchor(1), dblEpsilonValue
        Exit Sub
    End If
    
    ' --- Handle Start Anchor ---
    startAnchor(0) = vInitialStartAnchor(0): startAnchor(1) = vInitialStartAnchor(1): startAnchor(2) = vInitialStartAnchor(2)
    
    If (intGenDir = 1 And startAnchor(varyingCoordIdx) > dblBoundaryMax - dblEpsilonValue) Or _
       (intGenDir = -1 And startAnchor(varyingCoordIdx) < dblBoundaryMin + dblEpsilonValue) Then Exit Sub
    
    If blnAdjustStartAnchor Then
        collInfo = ClassifyFirstCollisionForPoint(startAnchor, dblClearanceRadius, collStructuresSS, objCurrentDrawing, DEFAULT_COLLISION_RATIO_THRESHOLD, dblEpsilonValue)
        If collInfo.CollisionOccurred Then
            tempAdjustedCoord = startAnchor(varyingCoordIdx)
            currentMaxRetreat = dblMaxRetreatForStartAnchor
            If blnAxisIsX Then
                adjusted = AdjustPointHorizontal(tempAdjustedCoord, startAnchor(fixedCoordIdx), intGenDir, dblClearanceRadius, collStructuresSS, currentMaxRetreat, dblPrevCoordForStartAnchorAdj, dblSpacing, dblBoundaryMin, dblBoundaryMax, dblEpsilonValue, objCurrentDrawing, collInfo, vP1, vP2, True)
            Else
                adjusted = AdjustPointVertical(tempAdjustedCoord, startAnchor(fixedCoordIdx), intGenDir, dblClearanceRadius, collStructuresSS, currentMaxRetreat, dblPrevCoordForStartAnchorAdj, dblSpacing, dblBoundaryMin, dblBoundaryMax, dblEpsilonValue, objCurrentDrawing, collInfo, vP1, vP2, True)
            End If
            If adjusted Then startAnchor(varyingCoordIdx) = tempAdjustedCoord Else Exit Sub
        End If
    End If
    
    ' Re-check StartAnchor
    If (intGenDir = 1 And startAnchor(varyingCoordIdx) > vInitialEndAnchor(varyingCoordIdx) + dblEpsilonValue) Or _
       (intGenDir = -1 And startAnchor(varyingCoordIdx) < vInitialEndAnchor(varyingCoordIdx) - dblEpsilonValue) Then Exit Sub
    If (intGenDir = 1 And startAnchor(varyingCoordIdx) > dblBoundaryMax - dblEpsilonValue) Or _
       (intGenDir = -1 And startAnchor(varyingCoordIdx) < dblBoundaryMin + dblEpsilonValue) Then Exit Sub

    AddPointToDictIfNotExist ioDictPoints, startAnchor(0), startAnchor(1), dblEpsilonValue
    currentPt(0) = startAnchor(0): currentPt(1) = startAnchor(1): currentPt(2) = startAnchor(2)
    Li_minus_1(0) = currentPt(0): Li_minus_1(1) = currentPt(1): Li_minus_1(2) = currentPt(2)

    ' --- Generate intermediate points ---
    loopCounter = 0
    currentMaxRetreat = standardMaxRetreatPassedAsParam

    Do While loopCounter < MAX_POINT_GENERATION_ITERATIONS_PER_LINE
        loopCounter = loopCounter + 1
        candidatePt(varyingCoordIdx) = currentPt(varyingCoordIdx) + intGenDir * dblSpacing
        candidatePt(fixedCoordIdx) = dblFixedCoordVal
        candidatePt(2) = 0

        ' Check if exceeding EndAnchor
        If (intGenDir = 1 And candidatePt(varyingCoordIdx) > vInitialEndAnchor(varyingCoordIdx) - dblEpsilonValue) Or _
           (intGenDir = -1 And candidatePt(varyingCoordIdx) < vInitialEndAnchor(varyingCoordIdx) + dblEpsilonValue) Then Exit Do
        
        ' Check boundary
        If (blnAxisIsX And (candidatePt(0) < dblBoundaryMin Or candidatePt(0) > dblBoundaryMax)) Or _
           (Not blnAxisIsX And (candidatePt(1) < dblBoundaryMin Or candidatePt(1) > dblBoundaryMax)) Then Exit Do

        collInfo = ClassifyFirstCollisionForPoint(candidatePt, dblClearanceRadius, collStructuresSS, objCurrentDrawing, DEFAULT_COLLISION_RATIO_THRESHOLD, dblEpsilonValue)
        If collInfo.CollisionOccurred Then
            tempAdjustedCoord = candidatePt(varyingCoordIdx)
            If blnAxisIsX Then
                adjusted = AdjustPointHorizontal(tempAdjustedCoord, dblFixedCoordVal, intGenDir, dblClearanceRadius, collStructuresSS, currentMaxRetreat, currentPt(varyingCoordIdx), dblSpacing, dblBoundaryMin, dblBoundaryMax, dblEpsilonValue, objCurrentDrawing, collInfo, vP1, vP2, False)
            Else
                adjusted = AdjustPointVertical(tempAdjustedCoord, dblFixedCoordVal, intGenDir, dblClearanceRadius, collStructuresSS, currentMaxRetreat, currentPt(varyingCoordIdx), dblSpacing, dblBoundaryMin, dblBoundaryMax, dblEpsilonValue, objCurrentDrawing, collInfo, vP1, vP2, False)
            End If
            If adjusted Then
                candidatePt(varyingCoordIdx) = tempAdjustedCoord
            Else
                Exit Do ' Stop if cannot avoid
            End If
        End If
        
        ' Re-check after adjustment
        If Abs(candidatePt(varyingCoordIdx) - currentPt(varyingCoordIdx)) > dblSpacing * 1.1 And loopCounter > 1 Then Exit Do
        If (intGenDir = 1 And candidatePt(varyingCoordIdx) > vInitialEndAnchor(varyingCoordIdx) - dblEpsilonValue) Or _
           (intGenDir = -1 And candidatePt(varyingCoordIdx) < vInitialEndAnchor(varyingCoordIdx) + dblEpsilonValue) Then Exit Do
        If (intGenDir = 1 And candidatePt(varyingCoordIdx) < currentPt(varyingCoordIdx) + dblEpsilonValue) Or _
           (intGenDir = -1 And candidatePt(varyingCoordIdx) > currentPt(varyingCoordIdx) - dblEpsilonValue) Then Exit Do

        AddPointToDictIfNotExist ioDictPoints, candidatePt(0), candidatePt(1), dblEpsilonValue
        currentPt(0) = candidatePt(0): currentPt(1) = candidatePt(1): currentPt(2) = candidatePt(2)
        Li_minus_1(0) = currentPt(0): Li_minus_1(1) = currentPt(1): Li_minus_1(2) = currentPt(2)
    Loop

    ' --- Handle End Anchor (Li) ---
    Li(0) = vInitialEndAnchor(0): Li(1) = vInitialEndAnchor(1): Li(2) = vInitialEndAnchor(2)
    
    If (intGenDir = 1 And Li(varyingCoordIdx) < startAnchor(varyingCoordIdx) + dblEpsilonValue And Abs(startAnchor(varyingCoordIdx) - vInitialStartAnchor(varyingCoordIdx)) > dblEpsilonValue) Or _
       (intGenDir = -1 And Li(varyingCoordIdx) > startAnchor(varyingCoordIdx) - dblEpsilonValue And Abs(startAnchor(varyingCoordIdx) - vInitialStartAnchor(varyingCoordIdx)) > dblEpsilonValue) Then Exit Sub
    
    If (blnAxisIsX And (Li(0) < dblBoundaryMin Or Li(0) > dblBoundaryMax)) Or _
       (Not blnAxisIsX And (Li(1) < dblBoundaryMin Or Li(1) > dblBoundaryMax)) Then Exit Sub

    If blnAdjustEndAnchor Then
        collInfo = ClassifyFirstCollisionForPoint(Li, dblClearanceRadius, collStructuresSS, objCurrentDrawing, DEFAULT_COLLISION_RATIO_THRESHOLD, dblEpsilonValue)
        If collInfo.CollisionOccurred Then
            tempAdjustedCoord = Li(varyingCoordIdx)
            currentMaxRetreat = standardMaxRetreatPassedAsParam
            If blnAxisIsX Then
                adjusted = AdjustPointHorizontal(tempAdjustedCoord, dblFixedCoordVal, intGenDir, dblClearanceRadius, collStructuresSS, currentMaxRetreat, Li_minus_1(varyingCoordIdx), dblSpacing, dblBoundaryMin, dblBoundaryMax, dblEpsilonValue, objCurrentDrawing, collInfo, vP1, vP2, True)
            Else
                adjusted = AdjustPointVertical(tempAdjustedCoord, dblFixedCoordVal, intGenDir, dblClearanceRadius, collStructuresSS, currentMaxRetreat, Li_minus_1(varyingCoordIdx), dblSpacing, dblBoundaryMin, dblBoundaryMax, dblEpsilonValue, objCurrentDrawing, collInfo, vP1, vP2, True)
            End If
            If adjusted Then Li(varyingCoordIdx) = tempAdjustedCoord Else Exit Sub
        End If
    End If
    
    ' Check Li again
    If (intGenDir = 1 And Li(varyingCoordIdx) < Li_minus_1(varyingCoordIdx) + dblEpsilonValue) Or _
       (intGenDir = -1 And Li(varyingCoordIdx) > Li_minus_1(varyingCoordIdx) - dblEpsilonValue) Then Exit Sub
    If (blnAxisIsX And (Li(0) < dblBoundaryMin Or Li(0) > dblBoundaryMax)) Or _
       (Not blnAxisIsX And (Li(1) < dblBoundaryMin Or Li(1) > dblBoundaryMax)) Then Exit Sub

    ' --- GAP HANDLING LOGIC ---
    dblDistanceToLi = Abs(Li(varyingCoordIdx) - Li_minus_1(varyingCoordIdx))
    currentMaxRetreat = standardMaxRetreatPassedAsParam

    If dblDistanceToLi > dblSpacing + dblEpsilonValue Then ' Case 2: D > spacing -> Insert points
        Dim tempGapPt(0 To 2) As Double
        Dim lastAddedToGap(0 To 2) As Double
        lastAddedToGap(0) = Li_minus_1(0): lastAddedToGap(1) = Li_minus_1(1): lastAddedToGap(2) = Li_minus_1(2)
        loopCounter = 0
        Do While loopCounter < MAX_POINT_GENERATION_ITERATIONS_PER_LINE
            loopCounter = loopCounter + 1
            tempGapPt(varyingCoordIdx) = lastAddedToGap(varyingCoordIdx) + intGenDir * dblSpacing
            tempGapPt(fixedCoordIdx) = dblFixedCoordVal
            tempGapPt(2) = 0

            ' Check if too close to Li
            If (intGenDir = 1 And tempGapPt(varyingCoordIdx) > Li(varyingCoordIdx) - dblSpacing + dblEpsilonValue) Or _
               (intGenDir = -1 And tempGapPt(varyingCoordIdx) < Li(varyingCoordIdx) + dblSpacing - dblEpsilonValue) Then Exit Do
            If (intGenDir = 1 And tempGapPt(varyingCoordIdx) >= Li(varyingCoordIdx) - dblEpsilonValue) Or _
               (intGenDir = -1 And tempGapPt(varyingCoordIdx) <= Li(varyingCoordIdx) + dblEpsilonValue) Then Exit Do

            collInfo = ClassifyFirstCollisionForPoint(tempGapPt, dblClearanceRadius, collStructuresSS, objCurrentDrawing, DEFAULT_COLLISION_RATIO_THRESHOLD, dblEpsilonValue)
            If collInfo.CollisionOccurred Then
                tempAdjustedCoord = tempGapPt(varyingCoordIdx)
                If blnAxisIsX Then
                    adjusted = AdjustPointHorizontal(tempAdjustedCoord, dblFixedCoordVal, intGenDir, dblClearanceRadius, collStructuresSS, currentMaxRetreat, lastAddedToGap(varyingCoordIdx), dblSpacing, dblBoundaryMin, dblBoundaryMax, dblEpsilonValue, objCurrentDrawing, collInfo, vP1, vP2, False)
                Else
                    adjusted = AdjustPointVertical(tempAdjustedCoord, dblFixedCoordVal, intGenDir, dblClearanceRadius, collStructuresSS, currentMaxRetreat, lastAddedToGap(varyingCoordIdx), dblSpacing, dblBoundaryMin, dblBoundaryMax, dblEpsilonValue, objCurrentDrawing, collInfo, vP1, vP2, False)
                End If
                If adjusted Then tempGapPt(varyingCoordIdx) = tempAdjustedCoord Else Exit Do
            End If
            
            ' Check again after adjustment
            If (intGenDir = 1 And tempGapPt(varyingCoordIdx) >= Li(varyingCoordIdx) - dblEpsilonValue) Or _
               (intGenDir = -1 And tempGapPt(varyingCoordIdx) <= Li(varyingCoordIdx) + dblEpsilonValue) Then Exit Do
            If (intGenDir = 1 And tempGapPt(varyingCoordIdx) < lastAddedToGap(varyingCoordIdx) + dblEpsilonValue) Or _
               (intGenDir = -1 And tempGapPt(varyingCoordIdx) > lastAddedToGap(varyingCoordIdx) - dblEpsilonValue) Then Exit Do

            AddPointToDictIfNotExist ioDictPoints, tempGapPt(0), tempGapPt(1), dblEpsilonValue
            lastAddedToGap(0) = tempGapPt(0): lastAddedToGap(1) = tempGapPt(1)
            Li_minus_1(0) = lastAddedToGap(0): Li_minus_1(1) = lastAddedToGap(1)
        Loop
        dblDistanceToLi = Abs(Li(varyingCoordIdx) - Li_minus_1(varyingCoordIdx))
    End If

    ' Handle final Li
    If dblDistanceToLi >= dblMinEdgeDistForGap - dblEpsilonValue And dblDistanceToLi <= dblSpacing + dblEpsilonValue Then ' Case 1
        AddPointToDictIfNotExist ioDictPoints, Li(0), Li(1), dblEpsilonValue
    ElseIf dblDistanceToLi < dblMinEdgeDistForGap - dblEpsilonValue And dblDistanceToLi > dblEpsilonValue Then ' Case 3: Reposition Li-1
        repositioned_Lminus1(varyingCoordIdx) = Li(varyingCoordIdx) - intGenDir * dblMinEdgeDistForGap
        repositioned_Lminus1(fixedCoordIdx) = dblFixedCoordVal
        repositioned_Lminus1(2) = 0
        
        Dim original_Li_minus_1_Key As String
        original_Li_minus_1_Key = GetCoordKey(Li_minus_1(0), dblEpsilonValue) & "|" & GetCoordKey(Li_minus_1(1), dblEpsilonValue)
        Dim success As Boolean: success = False
        
        collInfo = ClassifyFirstCollisionForPoint(repositioned_Lminus1, dblClearanceRadius, collStructuresSS, objCurrentDrawing, DEFAULT_COLLISION_RATIO_THRESHOLD, dblEpsilonValue)
        If collInfo.CollisionOccurred Then
            tempAdjustedCoord = repositioned_Lminus1(varyingCoordIdx)
            Dim prevForRepo As Double
            prevForRepo = Li(varyingCoordIdx) - intGenDir * (dblMinEdgeDistForGap + dblSpacing)
            Dim maxR As Double
            maxR = MaxVal(dblMinEdgeDistForGap, standardMaxRetreatPassedAsParam / 2)
            If maxR < RETREAT_STEP_MM And dblMinEdgeDistForGap >= RETREAT_STEP_MM Then maxR = dblMinEdgeDistForGap

            If blnAxisIsX Then
                adjusted = AdjustPointHorizontal(tempAdjustedCoord, dblFixedCoordVal, intGenDir, dblClearanceRadius, collStructuresSS, maxR, prevForRepo, dblSpacing, dblBoundaryMin, dblBoundaryMax, dblEpsilonValue, objCurrentDrawing, collInfo, vP1, vP2, True)
            Else
                adjusted = AdjustPointVertical(tempAdjustedCoord, dblFixedCoordVal, intGenDir, dblClearanceRadius, collStructuresSS, maxR, prevForRepo, dblSpacing, dblBoundaryMin, dblBoundaryMax, dblEpsilonValue, objCurrentDrawing, collInfo, vP1, vP2, True)
            End If
            If adjusted Then
                repositioned_Lminus1(varyingCoordIdx) = tempAdjustedCoord
                If Not ((intGenDir = 1 And repositioned_Lminus1(varyingCoordIdx) >= Li(varyingCoordIdx) - dblEpsilonValue) Or _
                        (intGenDir = -1 And repositioned_Lminus1(varyingCoordIdx) <= Li(varyingCoordIdx) + dblEpsilonValue)) Then
                    AddPointToDictIfNotExist ioDictPoints, repositioned_Lminus1(0), repositioned_Lminus1(1), dblEpsilonValue
                    success = True
                End If
            End If
        Else
            If Not ((intGenDir = 1 And repositioned_Lminus1(varyingCoordIdx) >= Li(varyingCoordIdx) - dblEpsilonValue) Or _
                    (intGenDir = -1 And repositioned_Lminus1(varyingCoordIdx) <= Li(varyingCoordIdx) + dblEpsilonValue)) Then
                AddPointToDictIfNotExist ioDictPoints, repositioned_Lminus1(0), repositioned_Lminus1(1), dblEpsilonValue
                success = True
            End If
        End If

        If success Then
            Dim repoKey As String
            repoKey = GetCoordKey(repositioned_Lminus1(0), dblEpsilonValue) & "|" & GetCoordKey(repositioned_Lminus1(1), dblEpsilonValue)
            If ioDictPoints.Exists(original_Li_minus_1_Key) And original_Li_minus_1_Key <> repoKey Then
                ioDictPoints.Remove original_Li_minus_1_Key
            End If
        End If
        AddPointToDictIfNotExist ioDictPoints, Li(0), Li(1), dblEpsilonValue
    ElseIf Abs(dblDistanceToLi) <= dblEpsilonValue Then
        AddPointToDictIfNotExist ioDictPoints, Li(0), Li(1), dblEpsilonValue
    Else
        AddPointToDictIfNotExist ioDictPoints, Li(0), Li(1), dblEpsilonValue
    End If

    Exit Sub
GenerateLineErrorHandler:
    Debug.Print "*** ERROR in GenerateLineOfPoints: " & Err.Description & " ***"
End Sub

' === FUNCTION TO DRAW CIRCLES (INNER AND OUTER) ===
Private Function DrawLashingHoleCircles(ByVal points As Collection, ByVal holeDia As Double, ByVal clearanceRad As Double, _
                                        ByRef createdInnerCircles As Collection, ByRef createdOuterCircles As Collection) As Boolean
    Dim pt As Variant, centerPt(0 To 2) As Double
    Dim holeLayerName As String, clearanceLayerName As String
    Dim oldActiveLayer As AcadLayer
    Dim innerCircle As AcadCircle, outerCircle As AcadCircle
    Dim tempLayerObj As AcadLayer

    On Error GoTo DrawCirclesErrHandler
    DrawLashingHoleCircles = False
    holeLayerName = "0"
    clearanceLayerName = "Mechanical-AM_9"
    
    Set createdInnerCircles = New Collection
    Set createdOuterCircles = New Collection
    
    ' Check layer
    On Error Resume Next
    Set tempLayerObj = ThisDrawing.Layers.Item(clearanceLayerName)
    If Err.Number <> 0 Then
        MsgBox "Layer '" & clearanceLayerName & "' does not exist.", vbCritical
        Exit Function
    End If
    On Error GoTo DrawCirclesErrHandler
    
    If points Is Nothing Or points.Count = 0 Then DrawLashingHoleCircles = True: Exit Function
    
    Set oldActiveLayer = ThisDrawing.ActiveLayer
    ThisDrawing.StartUndoMark
    
    For Each pt In points
        If VarType(pt) >= vbArray Then
            centerPt(0) = pt(0): centerPt(1) = pt(1): centerPt(2) = 0
            
            ' Draw Inner
            On Error Resume Next
            Set tempLayerObj = ThisDrawing.Layers.Item(holeLayerName)
            If Err.Number = 0 Then ThisDrawing.ActiveLayer = tempLayerObj
            On Error GoTo DrawCirclesErrHandler
            Set innerCircle = ThisDrawing.ModelSpace.AddCircle(centerPt, holeDia / 2)
            innerCircle.color = acByLayer
            createdInnerCircles.Add innerCircle
            
            ' Draw Outer
            On Error Resume Next
            Set tempLayerObj = ThisDrawing.Layers.Item(clearanceLayerName)
            If Err.Number = 0 Then ThisDrawing.ActiveLayer = tempLayerObj
            On Error GoTo DrawCirclesErrHandler
            Set outerCircle = ThisDrawing.ModelSpace.AddCircle(centerPt, clearanceRad)
            outerCircle.color = acByLayer
            createdOuterCircles.Add outerCircle
        End If
    Next pt
    
    ThisDrawing.EndUndoMark
    DrawLashingHoleCircles = True
    
    ' Restore layer
    On Error Resume Next
    If Not oldActiveLayer Is Nothing Then ThisDrawing.ActiveLayer = oldActiveLayer
    Exit Function

DrawCirclesErrHandler:
    MsgBox "Error in DrawLashingHoleCircles: " & Err.Description, vbCritical
    On Error Resume Next: ThisDrawing.EndUndoMark
    DrawLashingHoleCircles = False
End Function

' ==========================================================================================
'  PART 4: PHASE 2 & 3 - ADJUSTMENTS & AVOIDANCE
'  [FIXED] Restore Original "Stepping" Logic for 8-Direction Search & Ensure Inner Hole Move
' ==========================================================================================

Private Function PerformLocalAdjustments_Phase2( _
    ByRef collOuterCircles As Collection, ByRef collInnerCircles As Collection, _
    ByVal structuresSS As AcadSelectionSet, ByVal currentDrawing As AcadDocument, _
    ByVal clearanceRadiusVal As Double, ByVal epsilonValue As Double, _
    ByVal maxLocalAdjustLimitVal As Double, _
    ByVal absBoundMinX As Double, ByVal absBoundMaxX As Double, _
    ByVal absBoundMinY As Double, ByVal absBoundMaxY As Double, _
    ByVal mainBoundaryPline As AcadLWPolyline) As Collection

    Dim locallyAdjustedDims As Collection: Set locallyAdjustedDims = New Collection
    Set PerformLocalAdjustments_Phase2 = locallyAdjustedDims
    If collOuterCircles Is Nothing Then Exit Function

    Dim outerCircle As AcadCircle, innerCircle As AcadCircle
    Dim originalCenter As Variant, newCenter As Variant
    Dim i As Long, j As Long
    Dim tempPointFrom(0 To 2) As Double, tempPointTo(0 To 2) As Double
    Dim adjustmentType As String
    
    ThisDrawing.StartUndoMark
    
    For i = 1 To collOuterCircles.Count
        Set outerCircle = Nothing
        On Error Resume Next
        Set outerCircle = collOuterCircles(i)
        On Error GoTo 0
        
        If Not outerCircle Is Nothing Then
            If outerCircle.color = acRed Then
                originalCenter = outerCircle.Center
                
                ' [RESTORED] Find corresponding InnerCircle precisely
                Set innerCircle = Nothing
                For j = 1 To collInnerCircles.Count
                    Dim tempIn As AcadCircle
                    On Error Resume Next: Set tempIn = collInnerCircles(j): On Error GoTo 0
                    If Not tempIn Is Nothing Then
                        If Abs(tempIn.Center(0) - originalCenter(0)) < epsilonValue And _
                           Abs(tempIn.Center(1) - originalCenter(1)) < epsilonValue Then
                            Set innerCircle = tempIn
                            Exit For
                        End If
                    End If
                Next j
                
                ' Only process if both Inner and Outer holes are found
                If Not innerCircle Is Nothing Then
                    Dim collInfo As SimpleCollisionResult
                    collInfo = ClassifyFirstCollisionForPoint(originalCenter, clearanceRadiusVal, structuresSS, currentDrawing, DEFAULT_COLLISION_RATIO_THRESHOLD, epsilonValue)
                    newCenter = Empty
                    Dim shiftVal As Double
                    
                    ' Priority: Vertical -> Horizontal -> Complex (8 directions)
                    If collInfo.IsPrimarilyVerticalHit Then
                        newCenter = FindClosestSafeHorizontalShift_Local(originalCenter, clearanceRadiusVal, structuresSS, currentDrawing, epsilonValue, maxLocalAdjustLimitVal, absBoundMinX, absBoundMaxX, shiftVal)
                        adjustmentType = "Horizontal"
                    End If
                    If IsEmpty(newCenter) And collInfo.IsPrimarilyHorizontalHit Then
                        newCenter = FindClosestSafeVerticalShift_Local(originalCenter, clearanceRadiusVal, structuresSS, currentDrawing, epsilonValue, maxLocalAdjustLimitVal, absBoundMinY, absBoundMaxY, shiftVal)
                        adjustmentType = "Vertical"
                    End If
                    If IsEmpty(newCenter) Then
                        ' [RESTORED] 8-direction search logic scanning step by step
                        newCenter = FindBestSafeComplexShift_Local(originalCenter, clearanceRadiusVal, structuresSS, currentDrawing, epsilonValue, maxLocalAdjustLimitVal, absBoundMinX, absBoundMaxX, absBoundMinY, absBoundMaxY)
                        adjustmentType = "Complex"
                    End If
                    
                    If Not IsEmpty(newCenter) Then
                        ' Check if inside boundary
                        If IsPointInsidePolyline_Helper(newCenter, mainBoundaryPline, epsilonValue) Then
                            tempPointFrom(0) = originalCenter(0): tempPointFrom(1) = originalCenter(1): tempPointFrom(2) = 0
                            tempPointTo(0) = newCenter(0): tempPointTo(1) = newCenter(1): tempPointTo(2) = 0
                            
                            ' [FIXED] Perform Move for both holes and reset color
                            On Error Resume Next
                            outerCircle.Move tempPointFrom, tempPointTo
                            If Err.Number = 0 Then
                                innerCircle.Move tempPointFrom, tempPointTo ' Move inner hole immediately after outer hole
                                outerCircle.color = acByLayer
                                ' Add dimension
                                AddDimensionForAdjustedHole_Local locallyAdjustedDims, outerCircle, collOuterCircles, adjustmentType, epsilonValue, currentDrawing
                            Else
                                Debug.Print "Error moving hole: " & Err.Description
                            End If
                            On Error GoTo 0
                        End If
                    End If
                Else
                    Debug.Print "Inner Circle not found for Outer Circle Handle: " & outerCircle.Handle
                End If
            End If
        End If
    Next i
    
    ThisDrawing.EndUndoMark
End Function

Private Function PerformSpecialAreaAdjustment_Phase3( _
    ByRef ioCreatedInnerCircles As Collection, ByRef ioCreatedOuterCircles As Collection, _
    ByVal p1 As Variant, ByVal p2 As Variant, ByVal boundaryPline As AcadLWPolyline, _
    ByVal structuresSS As AcadSelectionSet, ByVal stdMaxRetreat As Double, _
    ByVal spacingX As Double, ByVal spacingY As Double, ByVal holeDiameter As Double, ByVal clearanceRadius As Double, _
    ByVal offsetY As Double, ByVal offsetX As Double, _
    ByVal B_abs_minX As Double, ByVal B_abs_maxX As Double, ByVal B_abs_minY As Double, ByVal B_abs_maxY As Double) As Collection

    On Error GoTo Phase3ErrorHandler
    ThisDrawing.StartUndoMark
    Dim phase3Dimensions As Collection: Set phase3Dimensions = New Collection
    Set PerformSpecialAreaAdjustment_Phase3 = phase3Dimensions
    
    Dim startHole As AcadCircle, endHole As AcadCircle
    Set startHole = SelectOuterCircle("Select START hole:", ioCreatedOuterCircles)
    If startHole Is Nothing Then GoTo ExitPhase3
    Set endHole = SelectOuterCircle("Select END hole:", ioCreatedOuterCircles)
    If endHole Is Nothing Or endHole.Handle = startHole.Handle Then GoTo ExitPhase3
    
    Dim dirChoice As String
    dirChoice = UCase(Trim(ThisDrawing.Utility.GetString(1, "Direction towards P1 or P2? [P1/P2]: ")))
    If dirChoice <> "P1" And dirChoice <> "P2" Then GoTo ExitPhase3
    
    Dim startCenter As Variant: startCenter = startHole.Center
    Dim endCenter As Variant: endCenter = endHole.Center
    Dim isVerticalRegen As Boolean
    
    If Abs(startCenter(1) - endCenter(1)) < DEFAULT_EPSILON Then isVerticalRegen = True Else isVerticalRegen = False
    
    Dim seedHoles As Collection: Set seedHoles = New Collection
    Dim c As AcadCircle, minCoord As Double, maxCoord As Double
    
    If isVerticalRegen Then
        minCoord = MinVal(startCenter(0), endCenter(0)): maxCoord = MaxVal(startCenter(0), endCenter(0))
        For Each c In ioCreatedOuterCircles
            If Abs(c.Center(1) - startCenter(1)) < DEFAULT_EPSILON And c.Center(0) >= minCoord - 0.1 And c.Center(0) <= maxCoord + 0.1 Then seedHoles.Add c
        Next c
    Else
        minCoord = MinVal(startCenter(1), endCenter(1)): maxCoord = MaxVal(startCenter(1), endCenter(1))
        For Each c In ioCreatedOuterCircles
            If Abs(c.Center(0) - startCenter(0)) < DEFAULT_EPSILON And c.Center(1) >= minCoord - 0.1 And c.Center(1) <= maxCoord + 0.1 Then seedHoles.Add c
        Next c
    End If
    
    If seedHoles.Count = 0 Then GoTo ExitPhase3
    Dim allNewPointsDict As Object: Set allNewPointsDict = CreateObject("Scripting.Dictionary")
    
    Dim seedHole As AcadCircle
    For Each seedHole In seedHoles
        Dim pointsCountBefore As Long: pointsCountBefore = allNewPointsDict.Count
        Dim seedPt As Variant: seedPt = seedHole.Center
        seedHole.color = acCyan
        
        Dim genDir As Integer
        If isVerticalRegen Then
            If dirChoice = "P1" Then genDir = Sgn(p1(1) - seedPt(1)) Else genDir = Sgn(p2(1) - seedPt(1))
        Else
            If dirChoice = "P1" Then genDir = Sgn(p1(0) - seedPt(0)) Else genDir = Sgn(p2(0) - seedPt(0))
        End If
        If genDir = 0 Then genDir = 1
        
        ' Cleaning old holes
        Dim i As Long
        For i = ioCreatedOuterCircles.Count To 1 Step -1
            Set c = ioCreatedOuterCircles(i)
            If c.Handle <> seedHole.Handle Then
                If isVerticalRegen Then
                    If Abs(c.Center(0) - seedPt(0)) < DEFAULT_EPSILON Then
                        If (genDir = 1 And c.Center(1) > seedPt(1)) Or (genDir = -1 And c.Center(1) < seedPt(1)) Then
                            ioCreatedOuterCircles.Remove i: c.Delete
                        End If
                    End If
                Else
                    If Abs(c.Center(1) - seedPt(1)) < DEFAULT_EPSILON Then
                        If (genDir = 1 And c.Center(0) > seedPt(0)) Or (genDir = -1 And c.Center(0) < seedPt(0)) Then
                            ioCreatedOuterCircles.Remove i: c.Delete
                        End If
                    End If
                End If
            End If
        Next i
        
        Dim k As Long
        For k = ioCreatedInnerCircles.Count To 1 Step -1
            Dim innerC As AcadCircle: Set innerC = ioCreatedInnerCircles(k)
            If Abs(innerC.Center(0) - seedPt(0)) > DEFAULT_EPSILON Or Abs(innerC.Center(1) - seedPt(1)) > DEFAULT_EPSILON Then
                 If isVerticalRegen Then
                    If Abs(innerC.Center(0) - seedPt(0)) < DEFAULT_EPSILON Then
                        If (genDir = 1 And innerC.Center(1) > seedPt(1)) Or (genDir = -1 And innerC.Center(1) < seedPt(1)) Then
                            ioCreatedInnerCircles.Remove k: innerC.Delete
                        End If
                    End If
                Else
                    If Abs(innerC.Center(1) - seedPt(1)) < DEFAULT_EPSILON Then
                        If (genDir = 1 And innerC.Center(0) > seedPt(0)) Or (genDir = -1 And innerC.Center(0) < seedPt(0)) Then
                            ioCreatedInnerCircles.Remove k: innerC.Delete
                        End If
                    End If
                End If
            End If
        Next k
        
        Dim newEndAnchor(0 To 2) As Double, dirVec(0 To 2) As Double
        If isVerticalRegen Then
            dirVec(1) = genDir: Dim intY As Variant: intY = FindIntersectionWithLongLine_Helper(seedPt, dirVec, boundaryPline)
            If Not IsEmpty(intY) Then newEndAnchor(0) = seedPt(0): newEndAnchor(1) = intY(1) - genDir * offsetY
        Else
            dirVec(0) = genDir: Dim intX As Variant: intX = FindIntersectionWithLongLine_Helper(seedPt, dirVec, boundaryPline)
            If Not IsEmpty(intX) Then newEndAnchor(0) = intX(0) - genDir * offsetX: newEndAnchor(1) = seedPt(1)
        End If
        
        Dim spacing As Double, bMin As Double, bMax As Double
        If isVerticalRegen Then spacing = spacingY: bMin = B_abs_minY: bMax = B_abs_maxY Else spacing = spacingX: bMin = B_abs_minX: bMax = B_abs_maxX
        
        RegenerateLineFromSeed_Special allNewPointsDict, seedPt, newEndAnchor, spacing, genDir, isVerticalRegen, clearanceRadius, structuresSS, ThisDrawing, stdMaxRetreat, p1, p2, bMin, bMax
        
        ' Dimensioning Phase 3
        If allNewPointsDict.Count > pointsCountBefore Then
             Dim ptsLine As Collection: Set ptsLine = New Collection
             Dim keyP As Variant, itemP As Variant
             For Each keyP In allNewPointsDict.Keys
                itemP = allNewPointsDict(keyP)
                If isVerticalRegen Then
                    If Abs(itemP(0) - seedPt(0)) < DEFAULT_EPSILON Then ptsLine.Add itemP(1)
                Else
                    If Abs(itemP(1) - seedPt(1)) < DEFAULT_EPSILON Then ptsLine.Add itemP(0)
                End If
             Next keyP
             
             Dim sortedC As Variant: sortedC = GetUniqueSortedValuesFromCollection(ptsLine, DEFAULT_EPSILON)
             If IsArray(sortedC) Then
                If UBound(sortedC) >= LBound(sortedC) + 1 Then
                    Dim dIdx As Long
                    Dim pt1(0 To 2) As Double, pt2(0 To 2) As Double, dLoc(0 To 2) As Double
                    Dim varIdx As Integer: If isVerticalRegen Then varIdx = 1 Else varIdx = 0
                    Dim fixIdx As Integer: fixIdx = 1 - varIdx
                    
                    For dIdx = LBound(sortedC) To UBound(sortedC) - 1
                        pt1(varIdx) = sortedC(dIdx): pt1(fixIdx) = seedPt(fixIdx)
                        pt2(varIdx) = sortedC(dIdx + 1): pt2(fixIdx) = seedPt(fixIdx)
                        
                        If isVerticalRegen Then
                            dLoc(0) = seedPt(0) + 150: dLoc(1) = (pt1(1) + pt2(1)) / 2
                        Else
                            dLoc(0) = (pt1(0) + pt2(0)) / 2: dLoc(1) = seedPt(1) + 150
                        End If
                        
                        If Abs(sortedC(dIdx) - sortedC(dIdx + 1)) > DEFAULT_EPSILON Then
                            Dim newD As AcadDimAligned
                            Set newD = ThisDrawing.ModelSpace.AddDimAligned(pt1, pt2, dLoc)
                            newD.Layer = "Mechanical-AM_9"
                            phase3Dimensions.Add newD
                        End If
                    Next dIdx
                End If
             End If
        End If
        seedHole.color = acByLayer
    Next seedHole
    
    ' 1. Ve cac vong tron moi tu danh sach diem da tinh toan
    Dim ptsToDraw As Collection: Set ptsToDraw = New Collection
    Dim kMap As Variant
    For Each kMap In allNewPointsDict.Keys
        Dim isSeed As Boolean: isSeed = False
        For Each seedHole In seedHoles
             If kMap = (GetCoordKey(seedHole.Center(0)) & "|" & GetCoordKey(seedHole.Center(1))) Then isSeed = True: Exit For
        Next seedHole
        If Not isSeed Then ptsToDraw.Add allNewPointsDict(kMap)
    Next kMap
    
    Dim nIn As Collection, nOut As Collection
    ' Ve thuc te len ban ve (mac dinh mau ByLayer)
    DrawLashingHoleCircles ptsToDraw, holeDiameter, clearanceRadius, nIn, nOut
    
    ' ==========================================================================
    ' [UPDATED LOGIC] HIGHLIGHT VA CHAM DE LOCAL ADJUSTMENT XU LY TIEP
    ' ==========================================================================
    Dim checkC As AcadCircle
    Dim checkRes As SimpleCollisionResult
    
    ' Duyet qua cac lo Outer vua moi tao ra
    For Each checkC In nOut
        ' Thuc hien kiem tra va cham lai mot lan nua
        ' Luc nay ta KHONG bo qua Horizontal/Vertical Hit nua ma se bat tat ca
        checkRes = ClassifyFirstCollisionForPoint(checkC.Center, clearanceRadius, structuresSS, ThisDrawing, 5#, DEFAULT_EPSILON)
        
        If checkRes.CollisionOccurred Then
            ' Neu co va cham (ke ca la ngang hay doc), chuyen sang mau DO
            ' De buoc Local Adjustment (Phase 2) sau do se nhan dien va xu ly
            checkC.color = acRed
        End If
        
        ' Them vao danh sach quan ly chung
        ioCreatedOuterCircles.Add checkC
    Next checkC
    
    For Each c In nIn: ioCreatedInnerCircles.Add c: Next
    ' ==========================================================================
    
ExitPhase3:
    ThisDrawing.EndUndoMark
    Exit Function
Phase3ErrorHandler:
    ThisDrawing.EndUndoMark
    Set PerformSpecialAreaAdjustment_Phase3 = New Collection
End Function

Private Sub RegenerateLineFromSeed_Special( _
    ByRef ioDictPoints As Object, ByVal seedPt As Variant, ByVal endPt As Variant, _
    ByVal spacing As Double, ByVal genDir As Integer, ByVal isVertical As Boolean, _
    ByVal clearanceRadius As Double, ByVal structuresSS As AcadSelectionSet, _
    ByVal currentDrawing As AcadDocument, ByVal stdMaxRetreat As Double, _
    ByVal p1 As Variant, ByVal p2 As Variant, _
    ByVal boundaryMin As Double, ByVal boundaryMax As Double)
    
    On Error GoTo RegenErrorHandler
    Dim varyingCoordIdx As Integer, fixedCoordIdx As Integer
    If isVertical Then varyingCoordIdx = 1: fixedCoordIdx = 0 Else varyingCoordIdx = 0: fixedCoordIdx = 1
    
    AddPointToDictIfNotExist ioDictPoints, seedPt(0), seedPt(1), DEFAULT_EPSILON
    Dim lastValid(0 To 2) As Double
    lastValid(0) = seedPt(0): lastValid(1) = seedPt(1): lastValid(2) = 0
    
    Dim loopCnt As Long: loopCnt = 0
    Do While loopCnt < MAX_POINT_GENERATION_ITERATIONS_PER_LINE
        loopCnt = loopCnt + 1
        Dim cand(0 To 2) As Double
        cand(varyingCoordIdx) = lastValid(varyingCoordIdx) + genDir * spacing
        cand(fixedCoordIdx) = seedPt(fixedCoordIdx)
        
        If (genDir = 1 And cand(varyingCoordIdx) > endPt(varyingCoordIdx) - DEFAULT_EPSILON) Or _
           (genDir = -1 And cand(varyingCoordIdx) < endPt(varyingCoordIdx) + DEFAULT_EPSILON) Then Exit Do
        
        If cand(varyingCoordIdx) < boundaryMin Or cand(varyingCoordIdx) > boundaryMax Then Exit Do
        
        Dim coll As SimpleCollisionResult
        coll = ClassifyFirstCollisionForPoint(cand, clearanceRadius, structuresSS, currentDrawing, DEFAULT_COLLISION_RATIO_THRESHOLD, DEFAULT_EPSILON)
        If coll.CollisionOccurred Then
            Dim adj As Boolean, tmp As Double: tmp = cand(varyingCoordIdx)
            If isVertical Then
                adj = AdjustPointVertical(tmp, cand(fixedCoordIdx), genDir, clearanceRadius, structuresSS, stdMaxRetreat, lastValid(varyingCoordIdx), spacing, boundaryMin, boundaryMax, DEFAULT_EPSILON, currentDrawing, coll, p1, p2, False)
            Else
                adj = AdjustPointHorizontal(tmp, cand(fixedCoordIdx), genDir, clearanceRadius, structuresSS, stdMaxRetreat, lastValid(varyingCoordIdx), spacing, boundaryMin, boundaryMax, DEFAULT_EPSILON, currentDrawing, coll, p1, p2, False)
            End If
            If adj Then cand(varyingCoordIdx) = tmp Else Exit Do
        End If
        
        If (genDir = 1 And cand(varyingCoordIdx) > endPt(varyingCoordIdx) - DEFAULT_EPSILON) Or _
           (genDir = -1 And cand(varyingCoordIdx) < endPt(varyingCoordIdx) + DEFAULT_EPSILON) Then Exit Do
            
        AddPointToDictIfNotExist ioDictPoints, cand(0), cand(1), DEFAULT_EPSILON
        lastValid(0) = cand(0): lastValid(1) = cand(1)
    Loop
    
    ' End Point Logic with isSeedAdj=True
    If (isVertical And (endPt(1) < boundaryMin Or endPt(1) > boundaryMax)) Or _
       (Not isVertical And (endPt(0) < boundaryMin Or endPt(0) > boundaryMax)) Then Exit Sub

    Dim collEnd As SimpleCollisionResult
    collEnd = ClassifyFirstCollisionForPoint(endPt, clearanceRadius, structuresSS, currentDrawing, DEFAULT_COLLISION_RATIO_THRESHOLD, DEFAULT_EPSILON)
    If collEnd.CollisionOccurred Then
        Dim finalAdjCoord As Double: finalAdjCoord = endPt(varyingCoordIdx)
        Dim adjEnd As Boolean
        If isVertical Then
            adjEnd = AdjustPointVertical(finalAdjCoord, endPt(fixedCoordIdx), genDir, clearanceRadius, structuresSS, stdMaxRetreat, lastValid(varyingCoordIdx), spacing, boundaryMin, boundaryMax, DEFAULT_EPSILON, currentDrawing, collEnd, p1, p2, True)
        Else
            adjEnd = AdjustPointHorizontal(finalAdjCoord, endPt(fixedCoordIdx), genDir, clearanceRadius, structuresSS, stdMaxRetreat, lastValid(varyingCoordIdx), spacing, boundaryMin, boundaryMax, DEFAULT_EPSILON, currentDrawing, collEnd, p1, p2, True)
        End If
        If adjEnd Then endPt(varyingCoordIdx) = finalAdjCoord Else Exit Sub
    End If
    
    If Abs(endPt(varyingCoordIdx) - lastValid(varyingCoordIdx)) > spacing * MIN_DIST_FACTOR_AFTER_RETREAT Then
        AddPointToDictIfNotExist ioDictPoints, endPt(0), endPt(1), DEFAULT_EPSILON
    End If
    Exit Sub
RegenErrorHandler:
End Sub

' === FUNCTION TO FIND SAFE HORIZONTAL POINT (BEST FIT) ===
Private Function FindClosestSafeHorizontalShift_Local( _
    ByVal originalCenter As Variant, ByVal clearanceRadius As Double, ByVal structuresSS As AcadSelectionSet, _
    ByVal currentDrawing As AcadDocument, ByVal epsilonValue As Double, ByVal maxLocalAdjustLimit As Double, _
    ByVal boundaryMinX As Double, ByVal boundaryMaxX As Double, ByRef outActualShift As Double) As Variant
    
    FindClosestSafeHorizontalShift_Local = Empty
    Dim steps As Long: steps = Int(maxLocalAdjustLimit / RETREAT_STEP_MM)
    Dim i As Long, testPt(0 To 2) As Double
    Dim bestLeft As Variant: bestLeft = Empty
    Dim bestRight As Variant: bestRight = Empty
    Dim distLeft As Double, distRight As Double
    
    ' Search Left
    For i = 1 To steps
        testPt(0) = originalCenter(0) - (i * RETREAT_STEP_MM): testPt(1) = originalCenter(1)
        If testPt(0) >= boundaryMinX Then
            Dim coll As SimpleCollisionResult: coll = ClassifyFirstCollisionForPoint(testPt, clearanceRadius, structuresSS, currentDrawing, DEFAULT_COLLISION_RATIO_THRESHOLD, epsilonValue)
            If Not coll.CollisionOccurred Then
                bestLeft = Array(testPt(0), testPt(1), 0): distLeft = i * RETREAT_STEP_MM: Exit For
            End If
        End If
    Next i
    
    ' Search Right
    For i = 1 To steps
        testPt(0) = originalCenter(0) + (i * RETREAT_STEP_MM): testPt(1) = originalCenter(1)
        If testPt(0) <= boundaryMaxX Then
            Dim coll2 As SimpleCollisionResult: coll2 = ClassifyFirstCollisionForPoint(testPt, clearanceRadius, structuresSS, currentDrawing, DEFAULT_COLLISION_RATIO_THRESHOLD, epsilonValue)
            If Not coll2.CollisionOccurred Then
                bestRight = Array(testPt(0), testPt(1), 0): distRight = i * RETREAT_STEP_MM: Exit For
            End If
        End If
    Next i
    
    ' Compare and select
    If Not IsEmpty(bestLeft) And Not IsEmpty(bestRight) Then
        If distLeft <= distRight Then
            FindClosestSafeHorizontalShift_Local = bestLeft: outActualShift = -distLeft
        Else
            FindClosestSafeHorizontalShift_Local = bestRight: outActualShift = distRight
        End If
    ElseIf Not IsEmpty(bestLeft) Then
        FindClosestSafeHorizontalShift_Local = bestLeft: outActualShift = -distLeft
    ElseIf Not IsEmpty(bestRight) Then
        FindClosestSafeHorizontalShift_Local = bestRight: outActualShift = distRight
    End If
End Function

' === FUNCTION TO FIND SAFE VERTICAL POINT (BEST FIT) ===
Private Function FindClosestSafeVerticalShift_Local( _
    ByVal originalCenter As Variant, ByVal clearanceRadius As Double, ByVal structuresSS As AcadSelectionSet, _
    ByVal currentDrawing As AcadDocument, ByVal epsilonValue As Double, ByVal maxLocalAdjustLimit As Double, _
    ByVal boundaryMinY As Double, ByVal boundaryMaxY As Double, ByRef outActualShift As Double) As Variant
    
    FindClosestSafeVerticalShift_Local = Empty
    Dim steps As Long: steps = Int(maxLocalAdjustLimit / RETREAT_STEP_MM)
    Dim i As Long, testPt(0 To 2) As Double
    Dim bestUp As Variant: bestUp = Empty
    Dim bestDown As Variant: bestDown = Empty
    Dim distUp As Double, distDown As Double
    
    ' Search Up
    For i = 1 To steps
        testPt(0) = originalCenter(0): testPt(1) = originalCenter(1) + (i * RETREAT_STEP_MM)
        If testPt(1) <= boundaryMaxY Then
            Dim coll As SimpleCollisionResult: coll = ClassifyFirstCollisionForPoint(testPt, clearanceRadius, structuresSS, currentDrawing, DEFAULT_COLLISION_RATIO_THRESHOLD, epsilonValue)
            If Not coll.CollisionOccurred Then
                bestUp = Array(testPt(0), testPt(1), 0): distUp = i * RETREAT_STEP_MM: Exit For
            End If
        End If
    Next i
    
    ' Search Down
    For i = 1 To steps
        testPt(0) = originalCenter(0): testPt(1) = originalCenter(1) - (i * RETREAT_STEP_MM)
        If testPt(1) >= boundaryMinY Then
            Dim coll2 As SimpleCollisionResult: coll2 = ClassifyFirstCollisionForPoint(testPt, clearanceRadius, structuresSS, currentDrawing, DEFAULT_COLLISION_RATIO_THRESHOLD, epsilonValue)
            If Not coll2.CollisionOccurred Then
                bestDown = Array(testPt(0), testPt(1), 0): distDown = i * RETREAT_STEP_MM: Exit For
            End If
        End If
    Next i
    
    ' Compare and select
    If Not IsEmpty(bestUp) And Not IsEmpty(bestDown) Then
        If distUp <= distDown Then
            FindClosestSafeVerticalShift_Local = bestUp: outActualShift = distUp
        Else
            FindClosestSafeVerticalShift_Local = bestDown: outActualShift = -distDown
        End If
    ElseIf Not IsEmpty(bestUp) Then
        FindClosestSafeVerticalShift_Local = bestUp: outActualShift = distUp
    ElseIf Not IsEmpty(bestDown) Then
        FindClosestSafeVerticalShift_Local = bestDown: outActualShift = -distDown
    End If
End Function

' === [RESTORED] FUNCTION TO FIND SAFE COMPLEX 8-DIRECTION POINT (BEST FIT) ===
Private Function FindBestSafeComplexShift_Local( _
    ByVal originalCenter As Variant, ByVal clearanceRadius As Double, ByVal structuresSS As AcadSelectionSet, _
    ByVal currentDrawing As AcadDocument, ByVal epsilonValue As Double, ByVal maxLocalAdjustLimit As Double, _
    ByVal boundaryMinX As Double, ByVal boundaryMaxX As Double, _
    ByVal boundaryMinY As Double, ByVal boundaryMaxY As Double) As Variant
    
    FindBestSafeComplexShift_Local = Empty
    Dim dirsX(7) As Double, dirsY(7) As Double, invSqrt2 As Double: invSqrt2 = 1 / Sqr(2)
    dirsX(0) = 0: dirsY(0) = 1: dirsX(1) = invSqrt2: dirsY(1) = invSqrt2: dirsX(2) = 1: dirsY(2) = 0: dirsX(3) = invSqrt2: dirsY(3) = -invSqrt2
    dirsX(4) = 0: dirsY(4) = -1: dirsX(5) = -invSqrt2: dirsY(5) = -invSqrt2: dirsX(6) = -1: dirsY(6) = 0: dirsX(7) = -invSqrt2: dirsY(7) = invSqrt2
    
    Dim i As Long, j As Long, testPt(0 To 2) As Double
    Dim bestPt As Variant: bestPt = Empty
    Dim minShiftDist As Double: minShiftDist = 1E+30
    
    ' Subdivide steps to find nearest point
    Dim steps As Long
    steps = Int(maxLocalAdjustLimit / RETREAT_STEP_MM)
    If steps = 0 And maxLocalAdjustLimit > epsilonValue Then steps = 1
    
    For i = 0 To 7 ' Scan through 8 directions
        For j = 1 To steps ' Scan small steps from near to far
            Dim currentDist As Double: currentDist = j * RETREAT_STEP_MM
            testPt(0) = originalCenter(0) + dirsX(i) * currentDist
            testPt(1) = originalCenter(1) + dirsY(i) * currentDist
            
            ' If current distance is already larger than min distance found, skip
            If currentDist > minShiftDist Then Exit For
            
            If testPt(0) >= boundaryMinX And testPt(0) <= boundaryMaxX And testPt(1) >= boundaryMinY And testPt(1) <= boundaryMaxY Then
                Dim coll As SimpleCollisionResult
                coll = ClassifyFirstCollisionForPoint(testPt, clearanceRadius, structuresSS, currentDrawing, DEFAULT_COLLISION_RATIO_THRESHOLD, epsilonValue)
                
                If Not coll.CollisionOccurred Then
                    ' Safe point found
                    If currentDist < minShiftDist Then
                        minShiftDist = currentDist
                        bestPt = Array(testPt(0), testPt(1), 0)
                    End If
                    ' Nearest safe point in this direction found, no need to scan further
                    Exit For
                End If
            Else
                ' Out of bounds
                Exit For
            End If
        Next j
    Next i
    
    FindBestSafeComplexShift_Local = bestPt
End Function

' === HELPER FUNCTIONS FOR AVOIDANCE LOGIC (KEPT AS IS) ===
Private Function AdjustInitialCenter8Dir(ByRef centerPt As Variant, ByVal clearanceRadius As Double, ByVal structuresSS As AcadSelectionSet, ByVal currentDrawing As AcadDocument, ByVal epsilonValue As Double, ByVal absBoundaryMinX As Double, ByVal absBoundaryMaxX As Double, ByVal absBoundaryMinY As Double, ByVal absBoundaryMaxY As Double, ByVal mainBoundaryPline As AcadLWPolyline) As Boolean
    Dim coll As SimpleCollisionResult
    coll = ClassifyFirstCollisionForPoint(centerPt, clearanceRadius, structuresSS, currentDrawing, DEFAULT_COLLISION_RATIO_THRESHOLD, epsilonValue)
    If Not coll.CollisionOccurred Then AdjustInitialCenter8Dir = True: Exit Function
    
    Dim dirsX(7) As Double, dirsY(7) As Double, invSqrt2 As Double: invSqrt2 = 1 / Sqr(2)
    dirsX(0) = 0: dirsY(0) = 1: dirsX(1) = invSqrt2: dirsY(1) = invSqrt2: dirsX(2) = 1: dirsY(2) = 0: dirsX(3) = invSqrt2: dirsY(3) = -invSqrt2
    dirsX(4) = 0: dirsY(4) = -1: dirsX(5) = -invSqrt2: dirsY(5) = -invSqrt2: dirsX(6) = -1: dirsY(6) = 0: dirsX(7) = -invSqrt2: dirsY(7) = invSqrt2
    
    Dim i As Long, res As Variant, maxDist As Double: maxDist = (2 * clearanceRadius) + 20
    For i = 0 To 7
        res = FindSafePointAlongDirection(centerPt, dirsX(i), dirsY(i), 5, maxDist, clearanceRadius, structuresSS, currentDrawing, epsilonValue, absBoundaryMinX, absBoundaryMaxX, absBoundaryMinY, absBoundaryMaxY, mainBoundaryPline)
        If Not IsEmpty(res) Then centerPt(0) = res(0): centerPt(1) = res(1): centerPt(2) = res(2): AdjustInitialCenter8Dir = True: Exit Function
    Next i
    AdjustInitialCenter8Dir = False
End Function

Private Function FindSafePointAlongDirection(ByVal originalPoint As Variant, ByVal dirX_unit As Double, ByVal dirY_unit As Double, ByVal stepIncrement As Double, ByVal maxSearchDistance As Double, ByVal clearanceRadius As Double, ByVal structuresSS As AcadSelectionSet, ByVal currentDrawing As AcadDocument, ByVal epsilonValue As Double, ByVal absBoundaryMinX As Double, ByVal absBoundaryMaxX As Double, ByVal absBoundaryMinY As Double, ByVal absBoundaryMaxY As Double, ByVal mainBoundaryPline As AcadLWPolyline) As Variant
    FindSafePointAlongDirection = Empty
    Dim steps As Long, i As Long, testPt(0 To 2) As Double
    steps = Int(maxSearchDistance / stepIncrement)
    For i = 1 To steps
        testPt(0) = originalPoint(0) + dirX_unit * stepIncrement * i: testPt(1) = originalPoint(1) + dirY_unit * stepIncrement * i: testPt(2) = originalPoint(2)
        If testPt(0) < absBoundaryMinX Or testPt(0) > absBoundaryMaxX Or testPt(1) < absBoundaryMinY Or testPt(1) > absBoundaryMaxY Then Exit For
        If Not IsPointInsidePolyline_Helper(testPt, mainBoundaryPline, epsilonValue) Then Exit For
        Dim coll As SimpleCollisionResult
        coll = ClassifyFirstCollisionForPoint(testPt, clearanceRadius, structuresSS, currentDrawing, DEFAULT_COLLISION_RATIO_THRESHOLD, epsilonValue)
        If Not coll.CollisionOccurred Then FindSafePointAlongDirection = Array(testPt(0), testPt(1), testPt(2)): Exit Function
    Next i
End Function

Private Function AdjustPointHorizontal(ByRef pointX As Double, ByVal baseY As Double, ByVal generationDirection As Integer, ByVal clearanceRadius As Double, ByVal structuresSS As AcadSelectionSet, ByVal maxRetreat As Double, ByVal previousValidPointX As Double, ByVal spacingX As Double, ByVal boundaryMinX As Double, ByVal boundaryMaxX As Double, ByVal epsilonValue As Double, ByVal currentDrawing As AcadDocument, initialCollisionInfo As SimpleCollisionResult, ByVal p1 As Variant, ByVal p2 As Variant, Optional ByVal isSeedAdj As Boolean = False) As Boolean
    Dim steps As Long, i As Long, retreatDir As Integer: retreatDir = -1 * generationDirection
    Dim testPt(0 To 2) As Double
    steps = Int(maxRetreat / RETREAT_STEP_MM)
    For i = 1 To steps
        Dim newX As Double: newX = pointX + (retreatDir * RETREAT_STEP_MM * i)
        If newX < boundaryMinX Or newX > boundaryMaxX Then Exit For
        If Not isSeedAdj Then
            If (retreatDir = generationDirection And Abs(newX - previousValidPointX) < spacingX * MIN_DIST_FACTOR_AFTER_RETREAT) Then Exit For
            If (retreatDir <> generationDirection) Then
               If (generationDirection = 1 And newX < previousValidPointX + spacingX * MIN_DIST_FACTOR_AFTER_RETREAT) Then Exit For
               If (generationDirection = -1 And newX > previousValidPointX - spacingX * MIN_DIST_FACTOR_AFTER_RETREAT) Then Exit For
            End If
        End If
        testPt(0) = newX: testPt(1) = baseY: testPt(2) = 0
        Dim coll As SimpleCollisionResult
        coll = ClassifyFirstCollisionForPoint(testPt, clearanceRadius, structuresSS, currentDrawing, DEFAULT_COLLISION_RATIO_THRESHOLD, epsilonValue)
        If Not coll.CollisionOccurred Then pointX = newX: AdjustPointHorizontal = True: Exit Function
    Next i
    AdjustPointHorizontal = False
End Function

Private Function AdjustPointVertical(ByRef pointY As Double, ByVal baseX As Double, ByVal generationDirection As Integer, ByVal clearanceRadius As Double, ByVal structuresSS As AcadSelectionSet, ByVal maxRetreat As Double, ByVal previousValidPointY As Double, ByVal spacingY As Double, ByVal boundaryMinY As Double, ByVal boundaryMaxY As Double, ByVal epsilonValue As Double, ByVal currentDrawing As AcadDocument, initialCollisionInfo As SimpleCollisionResult, ByVal p1 As Variant, ByVal p2 As Variant, Optional ByVal isSeedAdj As Boolean = False) As Boolean
    Dim steps As Long, i As Long, retreatDir As Integer: retreatDir = -1 * generationDirection
    Dim testPt(0 To 2) As Double
    steps = Int(maxRetreat / RETREAT_STEP_MM)
    For i = 1 To steps
        Dim newY As Double: newY = pointY + (retreatDir * RETREAT_STEP_MM * i)
        If newY < boundaryMinY Or newY > boundaryMaxY Then Exit For
        If Not isSeedAdj Then
            If (retreatDir = generationDirection And Abs(newY - previousValidPointY) < spacingY * MIN_DIST_FACTOR_AFTER_RETREAT) Then Exit For
            If (retreatDir <> generationDirection) Then
               If (generationDirection = 1 And newY < previousValidPointY + spacingY * MIN_DIST_FACTOR_AFTER_RETREAT) Then Exit For
               If (generationDirection = -1 And newY > previousValidPointY - spacingY * MIN_DIST_FACTOR_AFTER_RETREAT) Then Exit For
            End If
        End If
        testPt(0) = baseX: testPt(1) = newY: testPt(2) = 0
        Dim coll As SimpleCollisionResult
        coll = ClassifyFirstCollisionForPoint(testPt, clearanceRadius, structuresSS, currentDrawing, DEFAULT_COLLISION_RATIO_THRESHOLD, epsilonValue)
        If Not coll.CollisionOccurred Then pointY = newY: AdjustPointVertical = True: Exit Function
    Next i
    AdjustPointVertical = False
End Function
'**********************************************************************************************
'********************* AUTOMATICALLY SELECT STRUCTURES (UPDATED: AUTO-ZOOM FIX) ***************
'**********************************************************************************************
Public Function SelectStructuresByExample_Helper(bboxCoords As Variant) As AcadSelectionSet
    Dim ssResult As AcadSelectionSet
    Dim ssResName As String
    Dim filterTypeCode(0 To 7) As Integer
    Dim filterDataValue(0 To 7) As Variant
    
    ' 1. Setup Selection Set Name (Fixed name to avoid memory leak)
    ssResName = "SS_AutoStruct_Fixed"
    
    ' Always attempt to clear the old selection set first
    On Error Resume Next
    ThisDrawing.SelectionSets.Item(ssResName).Delete
    Err.Clear
    On Error GoTo SelStructErrorHandler

    ' 2. Create the Selection Set
    Set ssResult = ThisDrawing.SelectionSets.Add(ssResName)

    ' 3. Define Filters (Exclude Block & AM_11)
    filterTypeCode(0) = -4: filterDataValue(0) = "<AND"
        filterTypeCode(1) = -4: filterDataValue(1) = "<NOT"
        filterTypeCode(2) = 0:  filterDataValue(2) = "INSERT"
        filterTypeCode(3) = -4: filterDataValue(3) = "NOT>"
        
        filterTypeCode(4) = -4: filterDataValue(4) = "<NOT"
        filterTypeCode(5) = 8:  filterDataValue(5) = "Mechanical-AM_11"
        filterTypeCode(6) = -4: filterDataValue(6) = "NOT>"
    filterTypeCode(7) = -4: filterDataValue(7) = "AND>"

    ' 4. CALCULATE RECTANGLE & ZOOM (CRITICAL FIX)
    Dim i As Long
    Dim minX As Double, maxX As Double, minY As Double, maxY As Double
    Dim pt1(0 To 2) As Double, pt2(0 To 2) As Double
    
    If IsArray(bboxCoords) Then
        minX = bboxCoords(0): maxX = bboxCoords(0)
        minY = bboxCoords(1): maxY = bboxCoords(1)
        
        For i = 0 To UBound(bboxCoords) Step 3
            If bboxCoords(i) < minX Then minX = bboxCoords(i)
            If bboxCoords(i) > maxX Then maxX = bboxCoords(i)
            If bboxCoords(i + 1) < minY Then minY = bboxCoords(i + 1)
            If bboxCoords(i + 1) > maxY Then maxY = bboxCoords(i + 1)
        Next i
        
        ' Expand visual buffer slightly (10%) to ensure edges are visible
        Dim bufferX As Double, bufferY As Double
        bufferX = (maxX - minX) * 0.1
        bufferY = (maxY - minY) * 0.1
        
        pt1(0) = minX - bufferX: pt1(1) = minY - bufferY: pt1(2) = 0
        pt2(0) = maxX + bufferX: pt2(1) = maxY + bufferY: pt2(2) = 0
        
        ' [FIX] AUTO ZOOM TO AREA BEFORE SELECTING
        ' AutoCAD sometimes misses objects if they are off-screen.
        Dim currentView As Variant
        currentView = ThisDrawing.GetVariable("VIEWCTR") ' Save current view center (optional optimization)
        
        ThisDrawing.Application.ZoomWindow pt1, pt2
        
        ' Define selection points (Actual Bounding Box)
        Dim selPt1(0 To 2) As Double, selPt2(0 To 2) As Double
        selPt1(0) = minX: selPt1(1) = minY: selPt1(2) = 0
        selPt2(0) = maxX: selPt2(1) = maxY: selPt2(2) = 0
        
        ' Select Crossing Rectangle
        ssResult.Select acSelectionSetCrossing, selPt1, selPt2, filterTypeCode, filterDataValue
        
        ' Optional: Zoom Previous if you want to restore view (can be annoying if it jumps too much)
        ' ThisDrawing.Application.ZoomPrevious
    Else
        Set SelectStructuresByExample_Helper = Nothing
        Exit Function
    End If
    
    ' 5. Check Results
    If ssResult.Count = 0 Then
        ' Debug output to verify what happened
        Debug.Print "Zero objects found in Rect: " & minX & "," & minY & " to " & maxX & "," & maxY
        ThisDrawing.Utility.prompt vbCrLf & "-> No internal structures found."
        Set SelectStructuresByExample_Helper = Nothing
    Else
        ThisDrawing.Utility.prompt vbCrLf & "-> Auto-selected " & ssResult.Count & " objects."
        Set SelectStructuresByExample_Helper = ssResult
    End If
    
    Exit Function

SelStructErrorHandler:
    MsgBox "Error in SelectStructuresByExample_Helper: " & Err.Description, vbCritical
    If Not ssResult Is Nothing Then On Error Resume Next: ssResult.Delete
    Set SelectStructuresByExample_Helper = Nothing
End Function


' === FUNCTION TO CREATE KEEP-OUT ZONE FOR ADJACENT PANEL (VERTICAL) ===
Private Function AddAdjacentPanelKeepOutZones_Helper( _
    ByVal mainStructureCriteriaSS As AcadSelectionSet, _
    ByVal B_abs_minY As Double, ByVal B_abs_maxY As Double, _
    ByRef outKeepOutLinesCollection As Collection _
) As Boolean
    
    On Error GoTo HelperErrorHandler
    AddAdjacentPanelKeepOutZones_Helper = False

    Dim dictCriteria As Object: Set dictCriteria = CreateObject("Scripting.Dictionary")
    Dim obj As AcadEntity, criteriaKey As String
    
    If mainStructureCriteriaSS.Count = 0 Then Exit Function
    For Each obj In mainStructureCriteriaSS
        On Error Resume Next
        If TypeOf obj Is AcadLine Or TypeOf obj Is AcadLWPolyline Then
            criteriaKey = UCase(obj.Layer) & "|" & obj.color
            If Not dictCriteria.Exists(criteriaKey) Then dictCriteria.Add criteriaKey, True
        End If
        On Error GoTo HelperErrorHandler
    Next obj
    
    Dim adjacentSS As AcadSelectionSet
    Dim ssName As String: ssName = "TEMP_ADJACENT_SS_" & Format(Timer, "00000.00")
    On Error Resume Next: ThisDrawing.SelectionSets.Item(ssName).Delete: On Error GoTo HelperErrorHandler
    Set adjacentSS = ThisDrawing.SelectionSets.Add(ssName)
    
    ThisDrawing.Utility.prompt vbCrLf & "Select VERTICAL structures (LWPolyline) of adjacent panel..."
    Dim ft(0) As Integer, fd(0) As Variant
    ft(0) = 0: fd(0) = "LWPOLYLINE"
    adjacentSS.SelectOnScreen ft, fd
    
    If adjacentSS.Count = 0 Then adjacentSS.Delete: Exit Function
    
    Dim pline As AcadLWPolyline, pMin As Variant, pMax As Variant
    Dim deltaX As Double, deltaY As Double
    Dim lineObj1 As AcadLine, lineObj2 As AcadLine
    Dim ptStart(0 To 2) As Double, ptEnd(0 To 2) As Double
    Dim linesAddedCount As Long: linesAddedCount = 0
    
    For Each obj In adjacentSS
        If TypeOf obj Is AcadLWPolyline Then
            Set pline = obj
            criteriaKey = UCase(pline.Layer) & "|" & pline.color
            If dictCriteria.Exists(criteriaKey) Then
                On Error Resume Next
                pline.GetBoundingBox pMin, pMax
                If Err.Number = 0 Then
                    On Error GoTo HelperErrorHandler
                    deltaX = Abs(pMax(0) - pMin(0)): deltaY = Abs(pMax(1) - pMin(1))
                    If deltaX > DEFAULT_EPSILON And deltaY > ADJACENT_STRUCTURE_FILTER_RATIO * deltaX Then
                        ptStart(0) = pMin(0): ptStart(1) = B_abs_minY: ptStart(2) = 0
                        ptEnd(0) = pMin(0): ptEnd(1) = B_abs_maxY: ptEnd(2) = 0
                        Set lineObj1 = ThisDrawing.ModelSpace.AddLine(ptStart, ptEnd)
                        
                        ptStart(0) = pMax(0): ptStart(1) = B_abs_minY: ptStart(2) = 0
                        ptEnd(0) = pMax(0): ptEnd(1) = B_abs_maxY: ptEnd(2) = 0
                        Set lineObj2 = ThisDrawing.ModelSpace.AddLine(ptStart, ptEnd)
                        
                        If Not lineObj1 Is Nothing And Not lineObj2 Is Nothing Then
                            lineObj1.color = acMagenta: lineObj2.color = acMagenta
                            Dim itemsToAdd(0 To 1) As AcadEntity
                            Set itemsToAdd(0) = lineObj1: Set itemsToAdd(1) = lineObj2
                            On Error Resume Next
                            mainStructureCriteriaSS.AddItems itemsToAdd
                            If Err.Number = 0 Then
                                outKeepOutLinesCollection.Add lineObj1: outKeepOutLinesCollection.Add lineObj2
                                linesAddedCount = linesAddedCount + 2
                            Else
                                lineObj1.Delete: lineObj2.Delete
                            End If
                            On Error GoTo HelperErrorHandler
                        End If
                    End If
                End If
            End If
        End If
    Next obj
    
    If linesAddedCount > 0 Then AddAdjacentPanelKeepOutZones_Helper = True
    adjacentSS.Delete
    Exit Function
HelperErrorHandler:
    MsgBox "Error in AddAdjacentPanelKeepOutZones_Helper: " & Err.Description, vbCritical
    If Not adjacentSS Is Nothing Then On Error Resume Next: adjacentSS.Delete
    AddAdjacentPanelKeepOutZones_Helper = False
End Function

' === FUNCTION TO CREATE KEEP-OUT ZONE FOR ADJACENT PANEL (HORIZONTAL) ===
Private Function AddAdjacentPanelKeepOutZones_Horizontal_Helper( _
    ByVal mainStructureCriteriaSS As AcadSelectionSet, _
    ByVal B_abs_minX As Double, ByVal B_abs_maxX As Double, _
    ByRef outKeepOutLinesCollection As Collection _
) As Boolean
    
    On Error GoTo HelperErrorHandler
    AddAdjacentPanelKeepOutZones_Horizontal_Helper = False

    Dim dictCriteria As Object: Set dictCriteria = CreateObject("Scripting.Dictionary")
    Dim obj As AcadEntity, criteriaKey As String
    
    If mainStructureCriteriaSS.Count = 0 Then Exit Function
    For Each obj In mainStructureCriteriaSS
        On Error Resume Next
        If TypeOf obj Is AcadLine Or TypeOf obj Is AcadLWPolyline Then
            criteriaKey = UCase(obj.Layer) & "|" & obj.color
            If Not dictCriteria.Exists(criteriaKey) Then dictCriteria.Add criteriaKey, True
        End If
        On Error GoTo HelperErrorHandler
    Next obj
    
    Dim adjacentSS As AcadSelectionSet
    Dim ssName As String: ssName = "TEMP_ADJACENT_H_SS_" & Format(Timer, "00000.00")
    On Error Resume Next: ThisDrawing.SelectionSets.Item(ssName).Delete: On Error GoTo HelperErrorHandler
    Set adjacentSS = ThisDrawing.SelectionSets.Add(ssName)
    
    ThisDrawing.Utility.prompt vbCrLf & "Select HORIZONTAL structures (LWPolyline) of adjacent panel..."
    Dim ft(0) As Integer, fd(0) As Variant
    ft(0) = 0: fd(0) = "LWPOLYLINE"
    adjacentSS.SelectOnScreen ft, fd
    
    If adjacentSS.Count = 0 Then adjacentSS.Delete: Exit Function
    
    Dim pline As AcadLWPolyline, pMin As Variant, pMax As Variant
    Dim deltaX As Double, deltaY As Double
    Dim lineObj1 As AcadLine, lineObj2 As AcadLine
    Dim ptStart(0 To 2) As Double, ptEnd(0 To 2) As Double
    Dim linesAddedCount As Long: linesAddedCount = 0
    
    For Each obj In adjacentSS
        If TypeOf obj Is AcadLWPolyline Then
            Set pline = obj
            criteriaKey = UCase(pline.Layer) & "|" & pline.color
            If dictCriteria.Exists(criteriaKey) Then
                On Error Resume Next
                pline.GetBoundingBox pMin, pMax
                If Err.Number = 0 Then
                    On Error GoTo HelperErrorHandler
                    deltaX = Abs(pMax(0) - pMin(0)): deltaY = Abs(pMax(1) - pMin(1))
                    If deltaY > DEFAULT_EPSILON And deltaX > ADJACENT_STRUCTURE_FILTER_RATIO * deltaY Then
                        ' Bottom keep-out line
                        ptStart(0) = B_abs_minX: ptStart(1) = pMin(1): ptStart(2) = 0
                        ptEnd(0) = B_abs_maxX:   ptEnd(1) = pMin(1): ptEnd(2) = 0
                        Set lineObj1 = ThisDrawing.ModelSpace.AddLine(ptStart, ptEnd)
                        
                        ' Top keep-out line
                        ptStart(0) = B_abs_minX: ptStart(1) = pMax(1): ptStart(2) = 0
                        ptEnd(0) = B_abs_maxX:   ptEnd(1) = pMax(1): ptEnd(2) = 0
                        Set lineObj2 = ThisDrawing.ModelSpace.AddLine(ptStart, ptEnd)
                        
                        If Not lineObj1 Is Nothing And Not lineObj2 Is Nothing Then
                            lineObj1.color = acMagenta: lineObj2.color = acMagenta
                            Dim itemsToAdd(0 To 1) As AcadEntity
                            Set itemsToAdd(0) = lineObj1: Set itemsToAdd(1) = lineObj2
                            On Error Resume Next
                            mainStructureCriteriaSS.AddItems itemsToAdd
                            If Err.Number = 0 Then
                                outKeepOutLinesCollection.Add lineObj1: outKeepOutLinesCollection.Add lineObj2
                                linesAddedCount = linesAddedCount + 2
                            Else
                                lineObj1.Delete: lineObj2.Delete
                            End If
                            On Error GoTo HelperErrorHandler
                        End If
                    End If
                End If
            End If
        End If
    Next obj
    
    If linesAddedCount > 0 Then AddAdjacentPanelKeepOutZones_Horizontal_Helper = True
    adjacentSS.Delete
    Exit Function
HelperErrorHandler:
    MsgBox "Error in AddAdjacentPanelKeepOutZones_Horizontal_Helper: " & Err.Description, vbCritical
    If Not adjacentSS Is Nothing Then On Error Resume Next: adjacentSS.Delete
    AddAdjacentPanelKeepOutZones_Horizontal_Helper = False
End Function

' === FUNCTION TO CREATE CONTINUOUS DIMENSIONS (VERSION V2) ===
Private Function AddContinuousDimensions(ByVal points As Collection, _
    ByVal originPt As Variant, ByVal rect_minX As Double, ByVal rect_maxX As Double, _
    ByVal rect_minY As Double, ByVal rect_maxY As Double) As Collection
    
    Dim pt As Variant
    Dim dictRows As Object, dictCols As Object
    Dim rowKey As String, colKey As String
    Dim longestRowYKey As String, longestColXKey As String
    Dim longestRowY As Double, longestColX As Double
    Dim maxRowCount As Long, maxColCount As Long
    Dim dimObj As AcadDimAligned
    Dim targetDimLayer As AcadLayer
    Dim dimPlacementOffset As Double, dimLayerName As String
    Dim dimLineX As Double, dimLineY As Double
    Dim pt1(0 To 2) As Double, pt2(0 To 2) As Double, dimLoc(0 To 2) As Double
    Dim createdDimensions As Collection
    Dim idx As Long, objItemColl As Collection, key As Variant

    On Error GoTo DimErrorHandler
    Set createdDimensions = New Collection
    Set AddContinuousDimensions = createdDimensions

    dimPlacementOffset = 150#
    dimLayerName = "Mechanical-AM_9"
    
    

    If points Is Nothing Or points.Count < 1 Then Exit Function

    ' Classify points
    Set dictRows = CreateObject("Scripting.Dictionary")
    Set dictCols = CreateObject("Scripting.Dictionary")
    For Each pt In points
        If VarType(pt) >= vbArray Then
            rowKey = GetCoordKey(pt(1), DEFAULT_EPSILON)
            If Not dictRows.Exists(rowKey) Then Set dictRows(rowKey) = New Collection
            dictRows(rowKey).Add pt
            
            colKey = GetCoordKey(pt(0), DEFAULT_EPSILON)
            If Not dictCols.Exists(colKey) Then Set dictCols(colKey) = New Collection
            dictCols(colKey).Add pt
        End If
    Next pt

    ' Find longest row/col
    maxRowCount = 0
    If dictRows.Count > 0 Then
        For Each key In dictRows.Keys
            If dictRows(key).Count > maxRowCount Then
                maxRowCount = dictRows(key).Count: longestRowYKey = CStr(key)
            End If
        Next key
        If maxRowCount > 0 Then longestRowY = CDbl(longestRowYKey)
    End If
    
    maxColCount = 0
    If dictCols.Count > 0 Then
        For Each key In dictCols.Keys
            If dictCols(key).Count > maxColCount Then
                maxColCount = dictCols(key).Count: longestColXKey = CStr(key)
            End If
        Next key
        If maxColCount > 0 Then longestColX = CDbl(longestColXKey)
    End If

    ' Setup environment
    On Error Resume Next
    Set targetDimLayer = ThisDrawing.Layers.Item(dimLayerName)
    If targetDimLayer Is Nothing Then Set targetDimLayer = ThisDrawing.Layers.Add(dimLayerName): targetDimLayer.color = acYellow
    ThisDrawing.ActiveLayer = targetDimLayer
    ThisDrawing.SetVariable "DIMSCALE", targetDimscale
    On Error GoTo DimErrorHandler
    
    If maxRowCount > 0 Then dimLineY = longestRowY + dimPlacementOffset
    If maxColCount > 0 Then dimLineX = longestColX + dimPlacementOffset

    ThisDrawing.StartUndoMark

    ' --- CREATE HORIZONTAL DIMENSIONS ---
    If maxRowCount >= 1 Then
        Dim dimPointsX_Hole_Map As Object: Set dimPointsX_Hole_Map = CreateObject("Scripting.Dictionary")
        If dictRows.Exists(longestRowYKey) Then
            For Each pt In dictRows(longestRowYKey)
                colKey = GetCoordKey(pt(0), DEFAULT_EPSILON)
                If Not dimPointsX_Hole_Map.Exists(colKey) Then dimPointsX_Hole_Map.Add colKey, pt(0)
            Next pt
        End If
        
        If dimPointsX_Hole_Map.Count >= 1 Then
            Dim tempColl As Collection: Set tempColl = New Collection
            For Each key In dimPointsX_Hole_Map.Keys: tempColl.Add dimPointsX_Hole_Map(key): Next key
            Dim sortedX As Variant: sortedX = GetUniqueSortedValuesFromCollection(tempColl, DEFAULT_EPSILON)
            
            ' Find hole closest to P1
            Dim closestX As Double, minDistSq As Double: minDistSq = -1
            Dim foundClosest As Boolean: foundClosest = False
            
            If IsArray(sortedX) Then
                For idx = LBound(sortedX) To UBound(sortedX)
                    Dim dSq As Double: dSq = (sortedX(idx) - originPt(0)) ^ 2
                    If minDistSq < 0 Or dSq < minDistSq Then
                        minDistSq = dSq: closestX = sortedX(idx): foundClosest = True
                    End If
                Next idx
            End If
            
            ' Create first dimension (P1 -> Closest hole)
            If foundClosest Then
                pt1(0) = originPt(0): pt1(1) = longestRowY: pt1(2) = 0
                pt2(0) = closestX: pt2(1) = longestRowY: pt2(2) = 0
                If Abs(pt1(0) - pt2(0)) > DEFAULT_EPSILON Then
                    dimLoc(0) = (pt1(0) + pt2(0)) / 2: dimLoc(1) = dimLineY: dimLoc(2) = 0
                    Set dimObj = ThisDrawing.ModelSpace.AddDimAligned(pt1, pt2, dimLoc)
                    dimObj.ScaleFactor = targetDimscale
                    createdDimensions.Add dimObj
                End If
            End If
            
            ' Create continuous dimension chain
            Dim critX As Collection: Set critX = New Collection
            critX.Add originPt(0): critX.Add rect_minX: critX.Add rect_maxX
            If IsArray(sortedX) Then
                For idx = LBound(sortedX) To UBound(sortedX): critX.Add sortedX(idx): Next idx
            End If
            Dim chainX As Variant: chainX = GetUniqueSortedValuesFromCollection(critX, DEFAULT_EPSILON)
            
            If IsArray(chainX) Then
                For idx = LBound(chainX) To UBound(chainX) - 1
                    Dim sx1 As Double: sx1 = chainX(idx)
                    Dim sx2 As Double: sx2 = chainX(idx + 1)
                    Dim isDup As Boolean: isDup = False
                    If foundClosest Then
                        If (Abs(sx1 - originPt(0)) < DEFAULT_EPSILON And Abs(sx2 - closestX) < DEFAULT_EPSILON) Or _
                           (Abs(sx2 - originPt(0)) < DEFAULT_EPSILON And Abs(sx1 - closestX) < DEFAULT_EPSILON) Then isDup = True
                    End If
                    
                    If Not isDup And Abs(sx1 - sx2) > DEFAULT_EPSILON Then
                        pt1(0) = sx1: pt1(1) = longestRowY: pt1(2) = 0
                        pt2(0) = sx2: pt2(1) = longestRowY: pt2(2) = 0
                        dimLoc(0) = (pt1(0) + pt2(0)) / 2: dimLoc(1) = dimLineY: dimLoc(2) = 0
                        Set dimObj = ThisDrawing.ModelSpace.AddDimAligned(pt1, pt2, dimLoc)
                        dimObj.ScaleFactor = targetDimscale
                        createdDimensions.Add dimObj
                    End If
                Next idx
            End If
        End If
    End If

    ' --- CREATE VERTICAL DIMENSIONS ---
    If maxColCount >= 1 Then
        Dim dimPointsY_Hole_Map As Object: Set dimPointsY_Hole_Map = CreateObject("Scripting.Dictionary")
        If dictCols.Exists(longestColXKey) Then
            For Each pt In dictCols(longestColXKey)
                rowKey = GetCoordKey(pt(1), DEFAULT_EPSILON)
                If Not dimPointsY_Hole_Map.Exists(rowKey) Then dimPointsY_Hole_Map.Add rowKey, pt(1)
            Next pt
        End If
        
        If dimPointsY_Hole_Map.Count >= 1 Then
            Dim tempCollY As Collection: Set tempCollY = New Collection
            For Each key In dimPointsY_Hole_Map.Keys: tempCollY.Add dimPointsY_Hole_Map(key): Next key
            Dim sortedY As Variant: sortedY = GetUniqueSortedValuesFromCollection(tempCollY, DEFAULT_EPSILON)
            
            Dim closestY As Double, minDistSqY As Double: minDistSqY = -1
            Dim foundClosestY As Boolean: foundClosestY = False
            
            If IsArray(sortedY) Then
                For idx = LBound(sortedY) To UBound(sortedY)
                    Dim dSqY As Double: dSqY = (sortedY(idx) - originPt(1)) ^ 2
                    If minDistSqY < 0 Or dSqY < minDistSqY Then
                        minDistSqY = dSqY: closestY = sortedY(idx): foundClosestY = True
                    End If
                Next idx
            End If
            
            If foundClosestY Then
                pt1(0) = longestColX: pt1(1) = originPt(1): pt1(2) = 0
                pt2(0) = longestColX: pt2(1) = closestY: pt2(2) = 0
                If Abs(pt1(1) - pt2(1)) > DEFAULT_EPSILON Then
                    dimLoc(0) = dimLineX: dimLoc(1) = (pt1(1) + pt2(1)) / 2: dimLoc(2) = 0
                    Set dimObj = ThisDrawing.ModelSpace.AddDimAligned(pt1, pt2, dimLoc)
                    dimObj.ScaleFactor = targetDimscale
                    createdDimensions.Add dimObj
                End If
            End If
            
            Dim critY As Collection: Set critY = New Collection
            critY.Add originPt(1): critY.Add rect_minY: critY.Add rect_maxY
            If IsArray(sortedY) Then
                For idx = LBound(sortedY) To UBound(sortedY): critY.Add sortedY(idx): Next idx
            End If
            Dim chainY As Variant: chainY = GetUniqueSortedValuesFromCollection(critY, DEFAULT_EPSILON)
            
            If IsArray(chainY) Then
                For idx = LBound(chainY) To UBound(chainY) - 1
                    Dim sy1 As Double: sy1 = chainY(idx)
                    Dim sy2 As Double: sy2 = chainY(idx + 1)
                    Dim isDupY As Boolean: isDupY = False
                    If foundClosestY Then
                        If (Abs(sy1 - originPt(1)) < DEFAULT_EPSILON And Abs(sy2 - closestY) < DEFAULT_EPSILON) Or _
                           (Abs(sy2 - originPt(1)) < DEFAULT_EPSILON And Abs(sy1 - closestY) < DEFAULT_EPSILON) Then isDupY = True
                    End If
                    
                    If Not isDupY And Abs(sy1 - sy2) > DEFAULT_EPSILON Then
                        pt1(0) = longestColX: pt1(1) = sy1: pt1(2) = 0
                        pt2(0) = longestColX: pt2(1) = sy2: pt2(2) = 0
                        dimLoc(0) = dimLineX: dimLoc(1) = (pt1(1) + pt2(1)) / 2: dimLoc(2) = 0
                        Set dimObj = ThisDrawing.ModelSpace.AddDimAligned(pt1, pt2, dimLoc)
                        dimObj.ScaleFactor = targetDimscale
                        createdDimensions.Add dimObj
                    End If
                Next idx
            End If
        End If
    End If

    ThisDrawing.EndUndoMark
    Exit Function
DimErrorHandler:
    MsgBox "Error in AddContinuousDimensions: " & Err.Description
    On Error Resume Next: ThisDrawing.EndUndoMark
    Set AddContinuousDimensions = New Collection
End Function

' === FUNCTION TO ADD DIMENSION FOR LOCALLY ADJUSTED HOLE ===
Private Sub AddDimensionForAdjustedHole_Local( _
    ByRef dimCollection As Collection, ByVal adjustedOuterCircle As AcadCircle, _
    ByVal allOuterCircles As Collection, ByVal adjustmentType As String, _
    ByVal epsilonValue As Double, ByVal currentDrawing As AcadDocument _
)
    Dim adjustedCenter As Variant, refCircle As AcadCircle, refCenter As Variant
    Dim closestRefCenter As Variant
    Dim minDistSq As Double, currentDistSq As Double
    Dim pt1(0 To 2) As Double, pt2(0 To 2) As Double, dimLoc(0 To 2) As Double
    Dim dimObj As AcadDimAligned
    Dim targetDimLayer As AcadLayer


    On Error GoTo DimErr
    If adjustedOuterCircle Is Nothing Then Exit Sub
    adjustedCenter = adjustedOuterCircle.Center
    minDistSq = -1
    closestRefCenter = Empty
    
    On Error Resume Next
    Set targetDimLayer = currentDrawing.Layers.Item("Mechanical-AM_9")
    If targetDimLayer Is Nothing Then Set targetDimLayer = currentDrawing.Layers.Add("Mechanical-AM_9"): targetDimLayer.color = acYellow
    currentDrawing.ActiveLayer = targetDimLayer
    On Error GoTo DimErr

    ' Dimension X
    If adjustmentType = "Horizontal" Or adjustmentType = "Complex" Then
        minDistSq = -1
        closestRefCenter = Empty
        For Each refCircle In allOuterCircles
            If Not refCircle Is Nothing Then
                If Not refCircle Is adjustedOuterCircle And refCircle.color <> acRed Then
                    refCenter = refCircle.Center
                    If Abs(refCenter(1) - adjustedCenter(1)) < epsilonValue Then ' Same Y
                        currentDistSq = (refCenter(0) - adjustedCenter(0)) ^ 2
                        If minDistSq < 0 Or currentDistSq < minDistSq Then
                            minDistSq = currentDistSq: closestRefCenter = refCenter
                        End If
                    End If
                End If
            End If
        Next refCircle
        
        If Not IsEmpty(closestRefCenter) Then
            pt1(0) = adjustedCenter(0): pt1(1) = adjustedCenter(1): pt1(2) = 0
            pt2(0) = closestRefCenter(0): pt2(1) = adjustedCenter(1): pt2(2) = 0
            If Abs(pt1(0) - pt2(0)) > epsilonValue Then
                dimLoc(0) = (pt1(0) + pt2(0)) / 2
                dimLoc(1) = adjustedCenter(1) + LOCAL_ADJUST_DIM_OFFSET
                dimLoc(2) = 0
                Set dimObj = currentDrawing.ModelSpace.AddDimAligned(pt1, pt2, dimLoc)
                dimObj.ScaleFactor = targetDimscale
                dimObj.Update
                dimCollection.Add dimObj
            End If
        End If
    End If

    ' Dimension Y
    If adjustmentType = "Vertical" Or adjustmentType = "Complex" Then
        minDistSq = -1
        closestRefCenter = Empty
        For Each refCircle In allOuterCircles
            If Not refCircle Is Nothing Then
                If Not refCircle Is adjustedOuterCircle And refCircle.color <> acRed Then
                    refCenter = refCircle.Center
                    If Abs(refCenter(0) - adjustedCenter(0)) < epsilonValue Then ' Same X
                        currentDistSq = (refCenter(1) - adjustedCenter(1)) ^ 2
                        If minDistSq < 0 Or currentDistSq < minDistSq Then
                            minDistSq = currentDistSq: closestRefCenter = refCenter
                        End If
                    End If
                End If
            End If
        Next refCircle
        
        If Not IsEmpty(closestRefCenter) Then
            pt1(0) = adjustedCenter(0): pt1(1) = adjustedCenter(1): pt1(2) = 0
            pt2(0) = adjustedCenter(0): pt2(1) = closestRefCenter(1): pt2(2) = 0
            If Abs(pt1(1) - pt2(1)) > epsilonValue Then
                dimLoc(0) = adjustedCenter(0) + LOCAL_ADJUST_DIM_OFFSET
                dimLoc(1) = (pt1(1) + pt2(1)) / 2
                dimLoc(2) = 0
                Set dimObj = currentDrawing.ModelSpace.AddDimAligned(pt1, pt2, dimLoc)
                dimObj.ScaleFactor = targetDimscale
                dimCollection.Add dimObj
            End If
        End If
    End If
    Exit Sub
DimErr:
    Debug.Print "Error AddDimensionForAdjustedHole_Local: " & Err.Description
End Sub

' === FUNCTION TO CHECK COLLISIONS AND HIGHLIGHT RED ===
Private Sub CheckAndHighlightConflicts(ByVal clearanceCircles As Collection, ByVal structures As AcadSelectionSet)
    Dim circleObj As AcadCircle, structure As AcadEntity
    Dim res As SimpleCollisionResult
    Dim tempC As AcadCircle, centerPt(0 To 2) As Double
    
    If clearanceCircles Is Nothing Then Exit Sub
    If structures Is Nothing Then Exit Sub
    
    For Each circleObj In clearanceCircles
        On Error Resume Next
        centerPt(0) = circleObj.Center(0): centerPt(1) = circleObj.Center(1): centerPt(2) = circleObj.Center(2)
        Set tempC = ThisDrawing.ModelSpace.AddCircle(centerPt, circleObj.Radius)
        tempC.Visible = False
        
        For Each structure In structures
            res = ClassifyCollisionByFirstTwoPoints(tempC, structure, 5, 0.000001)
            If res.CollisionOccurred Then
                circleObj.color = acRed
                Exit For
            End If
        Next structure
        tempC.Delete
    Next circleObj
End Sub

' === FUNCTION TO COLLECT VALID ENTITIES FOR BLOCK ===
Private Sub CollectValidEntities(ByRef targetCollection As Collection, ByVal sourceCollection As Collection, ByVal sourceType As String)
    If sourceCollection Is Nothing Then Exit Sub
    Dim obj As Object
    For Each obj In sourceCollection
        On Error Resume Next
        If Not obj Is Nothing Then
            If Len(obj.Handle) > 0 Then targetCollection.Add obj
        End If
    Next obj
End Sub

' === OTHER UTILITY FUNCTIONS ===
Private Function GetCoordKey(ByVal coord As Double, Optional ByVal TOLERANCE As Double = DEFAULT_EPSILON) As String
    GetCoordKey = Format(coord, "0.000")
End Function

Private Sub AddPointToDictIfNotExist(ByVal dict As Object, ByVal x As Double, ByVal y As Double, ByVal epsilonValue As Double)
    Dim key As String: key = GetCoordKey(x) & "|" & GetCoordKey(y)
    If Not dict.Exists(key) Then
        Dim pt(0 To 2) As Double
        pt(0) = x: pt(1) = y: pt(2) = 0
        dict.Add key, pt
    End If
End Sub

Private Function GetUniqueSortedValuesFromCollection(ByVal inputColl As Collection, ByVal epsilon As Double) As Variant
    On Error Resume Next
    Dim dict As Object: Set dict = CreateObject("Scripting.Dictionary")
    Dim itm As Variant, val As Double, strKey As String
    
    ' Filter and add to Dictionary
    For Each itm In inputColl
        If IsNumeric(itm) Then
            val = CDbl(itm)
            strKey = GetCoordKey(val, epsilon)
            If Not dict.Exists(strKey) Then dict.Add strKey, val
        End If
    Next itm
    
    If dict.Count = 0 Then GetUniqueSortedValuesFromCollection = Empty: Exit Function
    
    Dim arr() As Double
    ReDim arr(0 To dict.Count - 1)
    Dim i As Long: i = 0
    Dim vKey As Variant ' Variant variable to iterate dictionary keys
    
    For Each vKey In dict.Keys
        arr(i) = dict(vKey)
        i = i + 1
    Next vKey
    
    ' Bubble Sort
    Dim j As Long, tmp As Double
    For i = LBound(arr) To UBound(arr) - 1
        For j = i + 1 To UBound(arr)
            If arr(i) > arr(j) Then
                tmp = arr(i): arr(i) = arr(j): arr(j) = tmp
            End If
        Next j
    Next i
    GetUniqueSortedValuesFromCollection = arr
End Function

Private Function SelectOuterCircle(ByVal prompt As String, ByVal circlesCollection As Collection) As AcadCircle
    Dim objEnt As AcadEntity, pt As Variant
    On Error Resume Next
    ThisDrawing.Utility.GetEntity objEnt, pt, vbCrLf & prompt
    If Err.Number = 0 And TypeOf objEnt Is AcadCircle Then
        ' Check if in collection
        Dim c As AcadCircle, found As Boolean: found = False
        For Each c In circlesCollection
            If c.Handle = objEnt.Handle Then found = True: Exit For
        Next c
        If found Then Set SelectOuterCircle = objEnt Else MsgBox "Hole does not belong to the generated group.", vbExclamation: Set SelectOuterCircle = Nothing
    Else
        Set SelectOuterCircle = Nothing
    End If
End Function

Private Function FindIntersectionWithLongLine_Helper(ByVal basePt As Variant, ByVal dirVector As Variant, ByVal pline As AcadLWPolyline) As Variant
    Dim lineObj As AcadLine
    Dim endPt(0 To 2) As Double
    endPt(0) = basePt(0) + dirVector(0) * 1000000
    endPt(1) = basePt(1) + dirVector(1) * 1000000
    endPt(2) = 0
    Set lineObj = ThisDrawing.ModelSpace.AddLine(basePt, endPt)
    Dim intPts As Variant
    intPts = lineObj.IntersectWith(pline, acExtendNone)
    lineObj.Delete
    
    If VarType(intPts) <> vbEmpty And IsArray(intPts) Then
        If UBound(intPts) >= 2 Then
            ' Find nearest point
            Dim minDistSq As Double: minDistSq = -1
            Dim bestPt(0 To 2) As Double
            Dim i As Long
            For i = 0 To UBound(intPts) Step 3
                Dim dSq As Double
                dSq = (intPts(i) - basePt(0)) ^ 2 + (intPts(i + 1) - basePt(1)) ^ 2
                If minDistSq < 0 Or dSq < minDistSq Then
                    minDistSq = dSq
                    bestPt(0) = intPts(i): bestPt(1) = intPts(i + 1): bestPt(2) = intPts(i + 2)
                End If
            Next i
            FindIntersectionWithLongLine_Helper = Array(bestPt(0), bestPt(1), bestPt(2))
        Else
            FindIntersectionWithLongLine_Helper = Empty
        End If
    Else
        FindIntersectionWithLongLine_Helper = Empty
    End If
End Function

' === END OF MODULE ===
